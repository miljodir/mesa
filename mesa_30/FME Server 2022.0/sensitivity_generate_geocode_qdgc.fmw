FME workspace sensitivity_generate_geocode_qdgc.fmw

Parameters:
- SourceDataset_GEOJSON = C:\Users\romslo\Norkart AS\MESA 3.0 - sensitivity atlas - General\Workspaces_romslo\polygon_rundt_vega.geojson   # Source GeoJSON File or URL
- FEATURE_TYPES =
- PARAMETER =   # Parameter Group
- delete_previous_grid = 1
- qdgc_levels = 2
- Projectname = romans_test_prosjekt   # Project name

Readers:
- GEOJSON_1: GEOJSON from $(SourceDataset_GEOJSON)

polygon_rundt_vega (reader GEOJSON_1)
    -> PROJReprojector_2
PROJReprojector_2
    DEST = EPSG:4326
    DEST_TAG = EPSG:4326
    INTERPOLATION_TYPE_NAME = Nearest Neighbor
    RASTER_CELL_SIZE = Preserve Cells
    RASTER_TOLERANCE = 0.0
    TRANSFORM_TYPE = Automatic Transformation
    REPROJECTED -> GeometryExtractor_3
GeometryExtractor_3
    ATTR = _geometry
    KIND_LONG = OGC Well Known Text
    OGCVERSION = 1.2
    OGC_WKT_PRECISION_DISPLAY = 64-bit
    REMOVE_GEOMETRY = No
    -> AttributeCreator_7
AttributeCreator_7
    ATTR_TABLE:
      SET_TO delete = FME_CONDITIONAL:DEFAULT_VALUE'0'BOOL_OP;OR;COMPOSITE_TEST;1;CASE_INSENSITIVE_TEST $(delete_previous_grid) CONTAINS 1'1'FME_NUM_CONDITIONS2___
      SET_TO query = FME_SQL_DELIMITER ;
        CREATE TABLE if not exists geocode.tbl_geocode_object
        (
            id character varying(20),
            area_reference character varying(50),
            level_qdgc integer,
            cellsize_degrees decimal,
            lon_center decimal,
            lat_center decimal,
            area_km2 decimal,
            geom geometry
        );
        SELECT * FROM qdgc_fillqdgc_rs('Norge',6,0,'geocode',ST_PolygonFromText('@Value(_geometry)',4326));
    -> SQLExecutor_3 [INITIATOR]
Note: qdgc grid into postgis to geocode database
SQLExecutor_3
    COMBINE_ATTRS = Result Attributes Only
    COMBINE_GEOM = Initiator Geometry Only
    DATASET = Mesa 3.0 - romslo
    FORMAT = POSTGRES
    OUTPUT_FEATURES_DISPLAY = Schema and Data Features
    POSTGRES_CREATE_FEATURE_TABLES_FROM_DATA = Yes
    POSTGRES_NAMED_CONNECTION = MESA 3.0
    POSTGRES_QUERY_FEATURE_TYPES_FOR_MERGE_FILTERS = Yes
    POSTGRES_READ_TIME_WITH_TIMEZONE = Yes
    SQL_STATEMENT = @Value(query)
