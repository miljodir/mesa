FME workspace sensitivity_staging.fmw

Parameters:
- Projectname = test   # Project name
- project_description =   # Project Description
- asset_data =   # Upload zip file with assets
- asset_group_name =   # Name of area that assets cover
- delete_previous_grid = 1   # Would you like to delete grid data from previous runs?
- geocode_grid = qdgc   # Would you like to system to generate QDGC geocode grid or upload own Grid?
- qdgc_levels_min = 1   # QDGC level min
- qdgc_levels_max = 2   # QDGC level max
- grid_data =   # If Own Grid selected; Upload zip file with grid data
- ref_user =   # Username
- user_token_provided =   # User token assosiated with
- Email =
- param_connectionstring_mesadatabase = Mesa 3.0 - romslo   # Connectionstring to mesa-database

Note: DataTimestamp START Tunnel
Junction_16
    -> Junction
Reprojector
    DEST = EPSG:4326
    INTERPOLATION_TYPE_NAME = Nearest Neighbor
    RASTER_CELL_SIZE = Preserve Cells
    RASTER_TOLERANCE = 0.0
    REPROJECTED -> Aggregator_6
    REPROJECTED -> AttributeKeeper_5
    REPROJECTED -> Junction_29
Junction_29
    -> BulkAttributeRemover_2
BulkAttributeRemover_2
    ATTR_EXP = (fme_|multi_reader|geopackage_|fme)
    -> AttributeRemover
AttributeRemover
    REMOVE_ATTRS = _creation_instance,_dirname,_dirpath,_extension,_filename,_matched_records,_rootname,approved_user,fme_dataset,fme_feature_type,fme_geometry{0},is_it_grid,path_accessed_date,path_created_date,path_directory_unix,path_directory_windows,path_extension,path_filename,path_filesize,path_modified_date,path_ownername,path_readonly,path_rootname,path_type,path_unix,path_windows,processing_start,projectname_scrubed,sum_read_from_database,token_user
    -> SchemaSetter [Input_2]
SchemaSetter
    ForceDataType = No
    SORT = Ascending
    Output_2 -> VariableRetriever_11
Junction_9
    -> CoordinateSystemExtractor
    -> UUIDGenerator_3
Junction_7
    -> CoordinateSystemExtractor
    -> UUIDGenerator_3
Note: FeatureReader_4 : Initiator
Junction_21
    -> Junction_22
Note: geocode Tunnel
Junction_13
    -> Junction_14
Note: geocode Tunnel
Junction_14
    -> Junction
Note: Project[code] summary
Junction_11
    -> Junction_12
Note: Project[code] summary
Junction_12
    -> Junction
Junction
    -> FeatureHolder

Bookmark: approved user?
Creator_2
    GEOMTYPE = Geometry Object
    NUM = 1
    CREATED -> DateTimeStamper_4
Note: DataTimestamp START Tunnel
Junction_15
    -> Junction_16
SQLExecutor
    ATTR_IGNORE_NULLS = Yes
    COMBINE_ATTRS = Keep Initiator Attributes if Conflict
    COMBINE_GEOM = Initiator Geometry Only
    DATASET = $(param_connectionstring_mesadatabase)
    EXPOSED_ATTRIBUTE_LIST = approved_user,id,token_user
    FORMAT = POSTGRES
    OUTPUT_FEATURES_DISPLAY = Schema and Data Features
    POSTGRES_CREATE_FEATURE_TABLES_FROM_DATA = Yes
    POSTGRES_NAMED_CONNECTION = MESA 3.0
    POSTGRES_QUERY_FEATURE_TYPES_FOR_MERGE_FILTERS = Yes
    POSTGRES_READ_TIME_WITH_TIMEZONE = Yes
    POSTGRES_SCHEMAS_FOR_TABLE_LISTING = system
    SQL_STATEMENT = select approved_user, id, token_user from system.tbl_user where email = '$(Email)' AND id = '$(ref_user)'
    RESULT -> Aggregator_5
    INITIATOR -> Aggregator_5
Aggregator_5
    ACCUM_ATTRS_NAME = Merge Incoming Attributes
    COUNT_ATTR = sum_read_from_database
    MODE = Attributes Only
    SEP = ,
    AGGREGATE -> TestFilter_8
TestFilter_8
    DEFAULT_VALUE = single user - passed
    TEST_LIST = "BOOL_OP,OR,COMPOSITE_TEST,""""""1"""""",TEST_CLAUSE,TEST @Value(sum_read_from_database) > 2",Duplicate users found in database,"BOOL_OP,OR,COMPOSITE_TEST,""""""1"""""",TEST_CLAUSE,TEST @Value(sum_read_from_database) = 1",User does not exist in database
    Duplicate users found in database -> AttributeCreator_message_duplicate_users
    User does not exist in database -> AttributeCreator_message_not_registered
    single user - passed -> TestFilter_9
TestFilter_9
    DEFAULT_VALUE = user token valid
    TEST_LIST = "BOOL_OP,OR,COMPOSITE_TEST,""""""1"""""",TEST_CLAUSE,TEST $(user_token_provided) != @Value(token_user)",user token not valid
    user token not valid -> AttributeCreator_message_invalid_token
    user token valid -> TestFilter_3
TestFilter_3
    DEFAULT_VALUE = user not approved
    TEST_LIST = "BOOL_OP,AND,COMPOSITE_TEST,""""""1"""""",TEST_CLAUSE,TEST @Value(approved_user) = t",approved user
    approved user -> AttributeCreator_11
    user not approved -> AttributeCreator_message_user_not_approved
Note: Send user parameters to Excel
Junction_19
    -> Junction_20

Bookmark: date_import
DateTimeStamper_4
    DATETIME_ATTR = processing_start
    INCLUDE_OFFSET = NO
    STAMP_TYPE = datetime
    TIMEZONE = utc
    -> DateTimeConverter_2
    -> Junction_15
DateTimeConverter_2
    DATETIME_ATTR = processing_start
    OUT_FORMAT = %Y-%m-%dT%H:%M:%S
    PASSTHROUGH = NO
    REPAIR_INPUT = YES
    -> SQLExecutor [INITIATOR]

Bookmark: Email administrator if error encountered. Terminate run
AttributeCreator_message_duplicate_users
    ATTR_TABLE = SET_TO meassage = there are duplicate users in database that are registered on same email adress.
    -> Emailer
AttributeCreator_message_not_registered
    ATTR_TABLE = SET_TO meassage = user is not registered in database
    -> Emailer
AttributeCreator_message_invalid_token
    ATTR_TABLE = SET_TO meassage = user provided invalid token
    -> Emailer
AttributeCreator_message_user_not_approved
    ATTR_TABLE = SET_TO meassage = user is not approved
    -> Emailer
Emailer
    BODY:
      The system encountered an error:

      @Value(meassage)

      Parameters from user:
      Username: $(ref_user)
      Email: $(Email)
      Projectname: $(Projectname)

      Action requered from administrator
    FROM = noreply@norkart.no
    SERVICE = Generic SMTP
    SMTP_CONNECTION = HOST;smtp.office365.com;PORT;587;ENCRYPTION;TLS;TIMEOUT;60;AUTHENTICATION;YES;USERNAME;smtpnorkart@norkart.no;PASSWORD;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;FME_CONTROLLER_QUERY_FILE;dependencies/Generic SMTP.fme;FME_CONTROLLER_CHOICE;Generic SMTP
    SUBJECT = SensitivityAtlas || System encountered a user approval error
    TO = b9e1c6be.miljodir.onmicrosoft.com@emea.teams.ms
    Sent -> Terminator
    <REJECTED> -> Terminator
Terminator
    MESSAGE = Translation Terminated

Bookmark: Ckeanup user input - remove whitespaces and such in projectname
Note: Test for whitespaces, non english characters and replace them with "_"
AttributeCreator_11
    ATTR_TABLE = SET_TO projectname_scrubed = @ReplaceRegularExpression(@ReplaceString(@LowerCase($(Projectname))," ","_",caseSensitive=FALSE),[^\x00-\x7F],"_",caseSensitive=FALSE)
    -> VariableSetter
VariableSetter
    SCOPE = Global
    VALUE = $(ref_user)_@Value(projectname_scrubed)
    VARNAME = p_name
    -> VariableRetriever
VariableRetriever
    SCOPE = Global
    VALUE_ATTR = p_name
    VARNAME = p_name
    -> SQLExecutor_6 [INITIATOR]
    -> Junction_19
    -> FilenamePartExtractor_2

Bookmark: Process asset files
FilenamePartExtractor_2
    DIRNAME_ATTR = _dirname
    DIRPATH_ATTR = _dirpath
    EXTENSION_ATTR = _extension
    FULLNAME_ATTR = _filename
    ROOTNAME_ATTR = _rootname
    SRC_ATTR = $(asset_data)
    -> AttributeFilter_2
AttributeFilter_2
    ATTR_NAME = _extension
    ATTR_VALUES = <Empty>,<Missing>,<Null>,<Unfiltered>,shp,SHP,geopackage,GEOPACKAGE,gpkg,GPKG,xml,XML,zip,ZIP
    shp -> Junction_24
    SHP -> Junction_24
    geopackage -> Junction_23
    GEOPACKAGE -> Junction_23
    gpkg -> Junction_23
    GPKG -> Junction_23
    xml -> Junction_25
    XML -> Junction_25
    zip -> FeatureReader [INITIATOR]
    ZIP -> FeatureReader [INITIATOR]

Bookmark: Read files - extra processing needed if zip
Junction_24
    -> Sampler
Junction_23
    -> Sampler_3
Junction_25
    -> Sampler_5
Junction_28
    -> Sampler_2
Junction_27
    -> Sampler_4
Junction_26
    -> Sampler_6

Bookmark: path assets
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Merge Initiator and Result
    ATTR_CONFLICT_RES = Use Result
    ATTR_IGNORE_NULLS = No
    COMBINE_GEOM = Use Result
    DATASET = $(asset_data)\**\/
    FEATURETYPES = PATH
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = YES
    PATH_TYPE = ANY
    PATH_USE_NON_STRING_ATTR = yes
    PATH -> AttributeCreator_13
AttributeCreator_13
    ATTR_TABLE = SET_TO _dirpath = $(asset_data)
    -> AttributeFilter_4
AttributeFilter_4
    ATTR_NAME = path_extension
    ATTR_VALUES = <Empty>,<Missing>,<Null>,<Unfiltered>,shp,SHP,geopackage,GEOPACKAGE,gpkg,GPKG,xml,XML
    shp -> Junction_4
    SHP -> Junction_4
    geopackage -> Junction_3
    GEOPACKAGE -> Junction_3
    gpkg -> Junction_3
    GPKG -> Junction_3
    xml -> Junction_2
    XML -> Junction_2

Bookmark: IF ZIP FILES - find what is zipped inside
Junction_4
    -> Sampler
Junction_3
    -> Sampler_3
Junction_2
    -> Sampler_5
Junction_6
    -> Sampler_2
Junction_8
    -> Sampler_4
Junction_5
    -> Sampler_6

Bookmark: shp assets
Sampler
    RATE = 1
    SAMPLE_MODE = No
    SAMPLE_TYPE_LONG = First N Features
    SAMPLED -> FeatureReader_shp_assets [INITIATOR]
FeatureReader_shp_assets
    ATTRS_TO_EXPOSE = fme_basename fme_dataset fme_feature_type
    ATTR_ACCUM_MODE = Merge Initiator and Result
    ATTR_CONFLICT_RES = Use Result
    ATTR_IGNORE_NULLS = No
    CACHE_TIMEOUT_HRS = 24
    COMBINE_GEOM = Use Result
    DATASET = @Value(_dirpath)\**\*.shp
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_SHAPEFILE_EXPOSE_FORMAT_ATTRS = fme_basename,char(50) fme_dataset,char(50) fme_feature_type,char(50)
    SHAPEFILE_TRIM_PRECEDING_SPACES = Yes
    SHAPEFILE_USE_SEARCH_ENVELOPE = NO
    <OTHER> -> AttributeCreator_18
AttributeCreator_18
    ATTR_TABLE = SET_TO is_it_grid = 0
    -> Reprojector
    -> Aggregator_6

Bookmark: gpkg assets
Sampler_3
    RATE = 1
    SAMPLE_MODE = No
    SAMPLE_TYPE_LONG = First N Features
    SAMPLED -> FeatureReader_gpkg_assets [INITIATOR]
FeatureReader_gpkg_assets
    ATTRS_TO_EXPOSE = fme_basename fme_dataset fme_feature_type
    ATTR_ACCUM_MODE = Merge Initiator and Result
    ATTR_CONFLICT_RES = Use Result
    ATTR_IGNORE_NULLS = No
    COMBINE_GEOM = Use Result
    DATASET = @Value(_dirpath)\**\*.gpkg
    FORMAT = GEOPACKAGE
    GEOPACKAGE_ENCODE_FEATURE_TYPE_AND_ATTR_NAMES = YES
    GEOPACKAGE_ENFORCE_FOREIGN_KEY_INTEGRITY = YES
    GEOPACKAGE_EXPOSE_PRIMARY_KEY_ATTRIBUTE = NO
    GEOPACKAGE_GEOPACKAGE_EXPOSE_FORMAT_ATTRS = fme_basename,text(50) fme_dataset,text(50) fme_feature_type,text(50) geopackage_fid,int geopackage_type,text(255)
    GEOPACKAGE_OPEN_SINGLE_RASTER_AS_SUBDATASET = YES
    GEOPACKAGE_QUERY_FEATURE_TYPES_FOR_MERGE_FILTERS = Yes
    GEOPACKAGE_READER_REPLACE_INVALID_CHARS = YES
    GEOPACKAGE_READ_BOOLEANS_AS_YES_NO = YES
    GEOPACKAGE_READ_NULLS = YES
    GEOPACKAGE_USE_SEARCH_ENVELOPE = NO
    INTERACT = NONE
    OUTPUT_FEATURES_DISPLAY = Schema and Data Features
    <OTHER> -> AttributeCreator_6
AttributeCreator_6
    ATTR_TABLE = SET_TO is_it_grid = 0
    -> Reprojector

Bookmark: managing assets_object and asset_groups
AttributeKeeper_5
    CREATE_BULK_MODE_FEATURES = NO
    KEEP_ATTRS = fme_feature_type,fme_basename,is_it_grid,date_import
    -> Aggregator_2
    -> FeatureMerger_4 [REQUESTOR]
BulkAttributeRemover
    ATTR_EXP = (fme_|multi_reader|geopackage_|fme)
    -> AttributeJSONPacker36
AttributeJSONPacker36
    PACKED = attribs
    -> UUIDGenerator
Note: id for asset_objects
UUIDGenerator
    UUID_ATTR = id
    -> GeometryFilter

Bookmark: id for asset_group
Aggregator_2
    ACCUM_ATTRS_NAME = Drop Incoming Attributes
    GROUP_BY = fme_feature_type
    MODE = Attributes Only
    SEP = ,
    AGGREGATE -> UUIDGenerator_5
UUIDGenerator_5
    UUID_ATTR = ref_asset_group
    -> FeatureMerger_4 [SUPPLIER]
FeatureMerger_4
    ATTR_ACCUM_MODE = Merge Supplier
    ATTR_CONFLICT_RES = Use Requestor
    IGNORE_NULLS = No
    JOIN_KEYS = @Value(fme_feature_type) @Value(fme_feature_type) AUTO
    MERGE_TYPE = Attributes Only
    PROCESS_DUPS = NO
    REJECT_NULL_MISSING_KEYS = No
    SUPPLIERS_FIRST = No
    MERGED -> BulkAttributeRemover
    MERGED -> CoordinateSystemExtractor

Bookmark: area size
GeometryFilter
    FILTER_MODE = SIMPLE
    FILTER_MULTI = FILTER_TYPES]Area]FME_CONTROLLER_QUERY_FILE]]FME_CONTROLLER_CHOICE]Simple
    Area -> AreaCalculator_2
    <UNFILTERED> -> GeometryRefiner
AreaCalculator_2
    AREA_ATTR = area_m2
    AREA_TYPE = Plane Area
    MULT = 1
    -> AttributeRounder
AttributeRounder
    PLACES = 0
    ROUND_TYPE = Up
    SRC_ATTRS = area_m2
    -> GeometryRefiner

Bookmark: feil i geometry?
GeometryRefiner
    -> GeometryValidator
GeometryValidator
    ISSUE_ATTR_NAME = _issues
    PRESETS = Custom
    REPAIR = Yes
    RULES = OGC_SIMPLE_CHECK FME_CONTROLLER_QUERY_FILE]transformers/dependencies/geometryvalidator8/OGC_SIMPLE_CHECK.fme]FME_CONTROLLER_CHOICE]OGC_SIMPLE_CHECK]LEGACY_OGC]No OGC_VALID_CHECK OGC_VERSION]V1.2.0]FME_CONTROLLER_QUERY_FILE]transformers\dependencies\geometryvalidator\OGC_VALID_CHECK.fme NULL_REMOVAL FME_CONTROLLER_QUERY_FILE]transformers/dependencies/geometryvalidator8/NULL_REMOVAL.fme]FME_CONTROLLER_CHOICE]NULL_REMOVAL NAN_REMOVAL PROCESS_MEASURE]NO]FME_CONTROLLER_QUERY_FILE]transformers/dependencies/geometryvalidator/NAN_REMOVAL.fme TYPE_REPAIR CONNECT_Z_MODE]IGNORE_Z]ARC_ENDPOINT_TOLERANCE_MODE]Auto]ARC_ENDPOINT_TOLERANCE]<Unused>]FME_CONTROLLER_QUERY_FILE]transformers/dependencies/geometryvalidator/TYPE_REPAIR.fme
    SUMMARY = Detailed
    PASSED -> AttributeCreator_17
    FAILED -> AttributeCreator_20
    REPAIRED -> AttributeCreator_17

Bookmark: process?
AttributeCreator_20
    ATTR_TABLE = SET_TO process = f
    -> AttributeManager_2
    -> AttributeRenamer
AttributeCreator_17
    ATTR_TABLE = SET_TO process = t
    -> AttributeManager_2

Bookmark: ASSET_OBJECTS WITH ISSUES
AttributeRenamer
    ATTR_TABLE = RENAME_SET_DEFAULT id > ref_asset_object
    MISSING_INPUT_ATTRS = REMOVE
    -> ListExploder
ListExploder
    ATTR_ACCUM_MODE = Merge List Attributes
    ATTR_CONFLICT_RES = Use List Attribute Values
    INDEX_ATTR = _element_index
    LIST_ATTR = _issues{}
    ELEMENTS -> AttributeCreator_4
AttributeCreator_4
    ATTR_TABLE = SET_TO issues_log = asset_object with id: @Value(ref_asset_object), in layer @Value(fme_feature_type) @Value(issue_found)
    -> UUIDGenerator_2

Bookmark: writing to project[code].tbl_asset_object
AttributeManager_2
    ATTR_TABLE:
      RENAME_SET_VALUE attribs > attributes
      SET_TO asset_group_name = $(asset_group_name)
      RENAME_SET_VALUE fme_feature_type > name_original
    -> PROJReprojector
PROJReprojector
    DEST = EPSG:4326
    DEST_TAG = EPSG:4326
    INTERPOLATION_TYPE_NAME = Nearest Neighbor
    RASTER_CELL_SIZE = Preserve Cells
    RASTER_TOLERANCE = 0.0
    TRANSFORM_TYPE = Automatic Transformation
    REPROJECTED -> VariableRetriever_5
    REPROJECTED -> Aggregator_9

Bookmark: Create tbl project and update
Aggregator_9
    ACCUM_ATTRS_NAME = Drop Incoming Attributes
    AGGREGATE_TYPE = Homogeneous Collection (If Possible)
    MODE = Geometry - Assemble One Level
    SEP = ,
    AGGREGATE -> BoundingBoxReplacer_3
BoundingBoxReplacer_3
    BOXTYPE = 2D Bounding Box
    BOX -> GeometryExtractor
GeometryExtractor
    ATTR = boundingbox
    KIND_LONG = Hex Encoded OGC Well Known Binary
    OGCVERSION = 1.2
    REMOVE_GEOMETRY = Yes
    -> VariableRetriever_3
VariableRetriever_3
    SCOPE = Global
    VALUE_ATTR = p_name
    VARNAME = p_name
    -> SQLExecutor_tbl_project [INITIATOR]
    -> FeatureWriter_system.tbl_project [Table100]

Bookmark: system
Note: system.tbl_project
FeatureWriter_system.tbl_project [off]
    DATASET = $(param_connectionstring_mesadatabase)
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = MESA 3.0
    POSTGRES_START_TRANSACTION = 0
    POSTGRES_STRICT_TEMPORAL_TYPE_HANDLING = Yes
    POSTGRES_TRANSACTION_INTERVAL = 1000
    TOTAL_FEATURES_WRITTEN_ATTR = _total_features_written
Note: system.tbl_project / project[code].tbl_project
SQLExecutor_tbl_project
    COMBINE_ATTRS = Result Attributes Only
    COMBINE_GEOM = Initiator Geometry Only
    DATASET = $(param_connectionstring_mesadatabase)
    FORMAT = POSTGRES
    OUTPUT_FEATURES_DISPLAY = Schema and Data Features
    POSTGRES_CREATE_FEATURE_TABLES_FROM_DATA = Yes
    POSTGRES_NAMED_CONNECTION = MESA 3.0
    POSTGRES_QUERY_FEATURE_TYPES_FOR_MERGE_FILTERS = Yes
    POSTGRES_READ_TIME_WITH_TIMEZONE = Yes
    POSTGRES_SCHEMAS_FOR_TABLE_LISTING = system
    SQL_STATEMENT:
      FME_SQL_DELIMITER ;
      CREATE TABLE if not exists system.tbl_project
      (
          id text UNIQUE,
          name text,
          description text,
          ref_user text,
          last_write timestamp,
          boundingbox geometry
      );
      CREATE TABLE if not exists @Value(p_name).tbl_project
      (
          id text UNIQUE,
          name text,
          description text,
          ref_user text,
          last_write timestamp,
          boundingbox geometry
      );

      INSERT INTO @Value(p_name).tbl_project (id, name, description, ref_user, last_write, boundingbox)
      VALUES (MD5('@Value(p_name)'), '@Value(p_name)', '$(project_description)', '$(ref_user)', NOW(), '@Value(boundingbox)')
      ON CONFLICT (id) DO UPDATE
        SET last_write = NOW(),
            boundingbox = '@Value(boundingbox)';

      INSERT INTO system.tbl_project (id, name, description, ref_user, last_write, boundingbox)
      VALUES (MD5('@Value(p_name)'), '@Value(p_name)', '$(project_description)', '$(ref_user)', NOW(), '@Value(boundingbox)')
      ON CONFLICT (id) DO UPDATE
        SET last_write = NOW(),
            boundingbox = '@Value(boundingbox)';
Note: system.tbl_processing / system.tbl_log
FeatureWriter_system.tbl_processing__system.tbl_log
    DATASET = $(param_connectionstring_mesadatabase)
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = MESA 3.0
    POSTGRES_START_TRANSACTION = 0
    POSTGRES_STRICT_TEMPORAL_TYPE_HANDLING = Yes
    POSTGRES_TRANSACTION_INTERVAL = 1000
    TOTAL_FEATURES_WRITTEN_ATTR = _total_features_written

Bookmark: Project[code]
VariableRetriever_5
    SCOPE = Global
    VALUE_ATTR = p_name
    VARNAME = p_name
    -> FeatureWriter__project_code_.tbl_asset_object [project.tbl_asset_object]
Note: project[code].tbl_asset_object
FeatureWriter__project_code_.tbl_asset_object
    DATASET = $(param_connectionstring_mesadatabase)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = MESA 3.0
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> Junction_11
VariableRetriever_11
    SCOPE = Global
    VALUE_ATTR = p_name
    VARNAME = p_name
    -> GeometryFilter_2
GeometryFilter_2
    FILTER_MODE = SIMPLE
    FILTER_MULTI = FILTER_TYPES]"Point Curve Surface Area"]FME_CONTROLLER_QUERY_FILE]]FME_CONTROLLER_CHOICE]Simple
    Point -> FeatureWriter_project_code_.tbl_asset_object_raw [project.tbl_geocode_group]
    Curve -> FeatureWriter_project_code_.tbl_asset_object_raw [Table1]
    Surface -> FeatureWriter_project_code_.tbl_asset_object_raw [Table100]
    Area -> FeatureWriter_project_code_.tbl_asset_object_raw [Table100]
Note: project[code].tbl_geocode_group
FeatureWriter_project_code_.tbl_asset_object_raw
    DATASET = $(param_connectionstring_mesadatabase)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = $(param_connectionstring_mesadatabase)
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
VariableRetriever_6
    SCOPE = Global
    VALUE_ATTR = p_name
    VARNAME = p_name
    -> FeatureWriter__project_code_.tbl_asset_group_issue [project.tbl_asset_group_issue]
Note: project[code].tbl_asset_group_issue
FeatureWriter__project_code_.tbl_asset_group_issue
    DATASET = $(param_connectionstring_mesadatabase)
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = $(param_connectionstring_mesadatabase)
    POSTGRES_START_TRANSACTION = 0
    POSTGRES_STRICT_TEMPORAL_TYPE_HANDLING = Yes
    POSTGRES_TRANSACTION_INTERVAL = 1000
    TOTAL_FEATURES_WRITTEN_ATTR = _total_features_written
    SUMMARY -> Junction_11
VariableRetriever_8
    SCOPE = Global
    VALUE_ATTR = p_name
    VARNAME = p_name
    -> FeatureWriter_project_code_.tbl_asset_group [project.tbl_asset_group]
Note: project[code].tbl_asset_group
Note: Truncate existing
FeatureWriter_project_code_.tbl_asset_group
    DATASET = $(param_connectionstring_mesadatabase)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = $(param_connectionstring_mesadatabase)
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> Junction_11
VariableRetriever_7
    SCOPE = Global
    VALUE_ATTR = p_name
    VARNAME = p_name
    -> FeatureWriter_projectcode.tbl_geocode_object [geocode.tbl_geocode_object00]
Note: Project[code].tbl_geocode_object
FeatureWriter_projectcode.tbl_geocode_object
    DATASET = $(param_connectionstring_mesadatabase)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = MESA 3.0
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> Junction_11
    SUMMARY -> Junction_21
VariableRetriever_4
    SCOPE = Global
    VALUE_ATTR = p_name
    VARNAME = p_name
    -> FeatureWriter_project_code_.tbl_geocode_group [project.tbl_geocode_group]
Note: project[code].tbl_geocode_group
FeatureWriter_project_code_.tbl_geocode_group
    DATASET = $(param_connectionstring_mesadatabase)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = MESA 3.0
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> Junction_11
Note: project[code].tbl_log
FeatureWriter_project_code.tbl_log
    DATASET = $(param_connectionstring_mesadatabase)
    DATASET_ATTR = _dataset
    FEATURE_TYPE_LIST_ATTR = _feature_types
    FORMAT = POSTGRES
    POSTGRES_BULK_COPY = YES
    POSTGRES_COORDINATE_SYSTEM_GRANULARITY = FEATURE
    POSTGRES_LOWERCASE_ATTRIBUTE_NAMES = Yes
    POSTGRES_NAMED_CONNECTION = MESA 3.0
    POSTGRES_START_TRANSACTION = 0
    POSTGRES_STRICT_TEMPORAL_TYPE_HANDLING = Yes
    POSTGRES_TRANSACTION_INTERVAL = 1000
    TOTAL_FEATURES_WRITTEN_ATTR = _total_features_written
    SUMMARY -> ParameterFetcher_3

Bookmark: to build grid from assets bbox - writing to project[code].tbl_geocode_object via postgis function
Aggregator_6
    ACCUM_ATTRS_NAME = Use Attributes From One Feature
    AGGREGATE_TYPE = Homogeneous Collection (If Possible)
    COUNT_ATTR = _feature_number
    MODE = Geometry - Assemble One Level
    SEP = ,
    AGGREGATE -> HullAccumulator
HullAccumulator
    3DMODE_PARAM = 2D
    ACCUM_INPUT_ATTRS = Use Attributes From One Feature
    HULLTYPE_PARAM = Convex ()
    HULL -> FeatureMerger_2 [REQUESTOR]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeKeeper_3
AttributeKeeper_3
    CREATE_BULK_MODE_FEATURES = NO
    KEEP_ATTRS = fme_feature_type,qdgc_levels
    -> Reprojector_2
Reprojector_2
    DEST = EPSG:4326
    INTERPOLATION_TYPE_NAME = Nearest Neighbor
    RASTER_CELL_SIZE = Preserve Cells
    RASTER_TOLERANCE = 0.0
    REPROJECTED -> TestFilter_2
Note: We need to generate new qdgc grid
Note: Acts as a IF ELSE statement to find if geocode contains grid for whole project area
Junction_10
    -> VariableRetriever_2
VariableRetriever_2
    SCOPE = Global
    VALUE_ATTR = p_name
    VARNAME = p_name
    -> GeometryExtractor_3
GeometryExtractor_3
    ATTR = _geometry
    KIND_LONG = OGC Well Known Text
    OGCVERSION = 1.2
    OGC_WKT_PRECISION_DISPLAY = 64-bit
    REMOVE_GEOMETRY = No
    -> AttributeCreator_7
AttributeCreator_7
    ATTR_TABLE:
      SET_TO delete = FME_CONDITIONAL:DEFAULT_VALUE'0'BOOL_OP;OR;COMPOSITE_TEST;1;CASE_INSENSITIVE_TEST $(delete_previous_grid) CONTAINS 1'1'FME_NUM_CONDITIONS2___
      SET_TO query = FME_SQL_DELIMITER ;
        CREATE TABLE if not exists @Value(p_name).tbl_geocode_object
        (
            id character varying(20),
            area_reference character varying(50),
            level_qdgc integer,
            cellsize_degrees decimal,
            lon_center decimal,
            lat_center decimal,
            area_km2 decimal,
            geom geometry
        );
        SELECT * FROM qdgc_fillqdgc_rs('$(asset_group_name)', $(qdgc_levels_min),$(qdgc_levels_max),@Value(delete),'@Value(p_name)',ST_PolygonFromText('@Value(_geometry)',4326));
    -> SQLExecutor_3 [INITIATOR]
Note: qdgc grid into postgis to project[code] database
SQLExecutor_3
    COMBINE_ATTRS = Result Attributes Only
    COMBINE_GEOM = Initiator Geometry Only
    DATASET = $(param_connectionstring_mesadatabase)
    FORMAT = POSTGRES
    OUTPUT_FEATURES_DISPLAY = Schema and Data Features
    POSTGRES_CREATE_FEATURE_TABLES_FROM_DATA = Yes
    POSTGRES_NAMED_CONNECTION = MESA 3.0
    POSTGRES_QUERY_FEATURE_TYPES_FOR_MERGE_FILTERS = Yes
    POSTGRES_READ_TIME_WITH_TIMEZONE = Yes
    SQL_STATEMENT = @Value(query)

Bookmark: shp.xml assets
Sampler_5
    RATE = 1
    SAMPLE_MODE = No
    SAMPLE_TYPE_LONG = First N Features
    SAMPLED -> FeatureReader_shp.xml_grids_2 [INITIATOR]
FeatureReader_shp.xml_grids_2
    ATTRS_TO_EXPOSE = fme_basename fme_dataset fme_feature_type Esri.CreaDate
    ATTR_ACCUM_MODE = Merge Initiator and Result
    ATTR_CONFLICT_RES = Use Result
    ATTR_IGNORE_NULLS = No
    COMBINE_GEOM = Use Result
    DATASET = @Value(_dirpath)\**\*.shp.xml
    FORMAT = XML
    INTERACT = NONE
    OUTPUT_FEATURES_DISPLAY = Schema and Data Features
    XML_CONTINUE_ON_GEOM_ERROR = yes
    XML_FILE_TYPE = Feature Paths
    XML_SUPPORTED_READER_ARCHIVE_EXTENSIONS = xml.gz,gml.gz
    XML_USE_SEARCH_ENVELOPE = NO
    XML_VALIDATE_DATASET = no
    XML_VALIDATE_XFMAP = no
    XML_XFMAP_FEATURE_PATHS = metadata
    XML_XFMAP_FEATURE_PATHS_STRUCTURE = <structure separator="." map-empty-elements="yes" matched-prefix="attributes" matched-attributes="yes" cardinality="+{?}" structure-prefix="" child-position-attribute="" except-expression="" ui-mode="basic" matched-ancestor-attributes=""/>
    XML_XML_EXPOSE_FORMAT_ATTRS = fme_basename,xml_char(50) fme_dataset,xml_char(50) fme_feature_type,xml_char(50)
    <OTHER> -> Aggregator_3

Bookmark: EXCEL OUTPUT FOR EDITING
Note: Send user parameters to Excel
Junction_20
    -> DateTimeStamper
DateTimeStamper
    DATETIME_ATTR = _timestamp
    STAMP_TYPE = date
    TIMEZONE = local
    -> ParameterFetcher
Note: Neccessary for writing projectname in Excel file name.
ParameterFetcher
    ATTR_LIST = _Projectname $(Projectname)
    -> Sorter
Sorter
    SORT_PARM = _count NATURAL DESCENDING
    SORTED -> TestFilter_10
TestFilter_10
    DEFAULT_VALUE = Appendix1
    TEST_LIST = "BOOL_OP,OR,COMPOSITE_TEST,""""""1"""""",TEST_CLAUSE,TEST token_user ATTRIBUTE_HAS_A_VALUE """,sys_param
    sys_param -> FeatureWriter_excel_output [Sheet1]
    Appendix1 -> Sorter_4
    Appendix1 -> AttributeCreator_9
Note: sort file assets to be first
Sorter_4
    SORT_PARM = is_it_grid NUMERIC ASCENDING _count NUMERIC ASCENDING
    SORTED -> FeatureWriter_excel_output [Output]
FeatureWriter_excel_output
    DATASET = @Value(_Projectname)_sensitivity_values_@Value(_timestamp).xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_DESTINATION_DATASETTYPE_VALIDATION = Yes
    XLSXW_DROP_TABLE = No
    XLSXW_FIELD_NAMES_FORMATTING = Yes
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
    SUMMARY -> Junction_13

Bookmark: Create project[code] schema if nesccesary
SQLExecutor_6
    ATTR_IGNORE_NULLS = Yes
    COMBINE_ATTRS = Keep Initiator Attributes if Conflict
    COMBINE_GEOM = Initiator Geometry Only
    DATASET = $(param_connectionstring_mesadatabase)
    FORMAT = POSTGRES
    OUTPUT_FEATURES_DISPLAY = Schema and Data Features
    POSTGRES_CREATE_FEATURE_TABLES_FROM_DATA = Yes
    POSTGRES_NAMED_CONNECTION = MESA 3.0
    POSTGRES_QUERY_FEATURE_TYPES_FOR_MERGE_FILTERS = Yes
    POSTGRES_READ_TIME_WITH_TIMEZONE = Yes
    POSTGRES_SCHEMAS_FOR_TABLE_LISTING = system
    SQL_STATEMENT:
      FME_SQL_DELIMITER ;
      create schema if not exists @Value(p_name);
    INITIATOR -> TestFilter_12
    INITIATOR -> Aggregator_7
TestFilter_12
    DEFAULT_VALUE = do not delete previous
    TEST_LIST = "BOOL_OP,OR,COMPOSITE_TEST,""""""1"""""",TEST_CLAUSE,CASE_INSENSITIVE_TEST $(delete_previous_grid) CONTAINS 1",delete previous
    delete previous -> SQLExecutor_4 [INITIATOR]
Note: Drop old grid if delete previous option is true
SQLExecutor_4
    COMBINE_ATTRS = Result Attributes Only
    COMBINE_GEOM = Initiator Geometry Only
    DATASET = $(param_connectionstring_mesadatabase)
    FORMAT = POSTGRES
    OUTPUT_FEATURES_DISPLAY = Schema and Data Features
    POSTGRES_CREATE_FEATURE_TABLES_FROM_DATA = Yes
    POSTGRES_NAMED_CONNECTION = MESA 3.0
    POSTGRES_QUERY_FEATURE_TYPES_FOR_MERGE_FILTERS = Yes
    POSTGRES_READ_TIME_WITH_TIMEZONE = Yes
    POSTGRES_SCHEMAS_FOR_TABLE_LISTING = system
    SQL_STATEMENT:
      FME_SQL_DELIMITER ;
      DROP TABLE IF EXISTS @Value(p_name).tbl_geocode_object;
    INITIATOR -> Aggregator_7
Aggregator_7
    ACCUM_ATTRS_NAME = Use Attributes From One Feature
    MODE = Attributes Only
    SEP = ,
    AGGREGATE -> TestFilter_6

Bookmark: custom grid?
TestFilter_6
    DEFAULT_VALUE = custom grid
    TEST_LIST = "BOOL_OP,OR,COMPOSITE_TEST,""""""1"""""",TEST_CLAUSE,TEST $(geocode_grid) = qdgc",qdgc grid
    qdgc grid -> FeatureMerger_2 [SUPPLIER]
    custom grid -> FilenamePartExtractor_3

Bookmark: Process grid files
FilenamePartExtractor_3
    DIRNAME_ATTR = _dirname
    DIRPATH_ATTR = _dirpath
    EXTENSION_ATTR = _extension
    FULLNAME_ATTR = _filename
    ROOTNAME_ATTR = _rootname
    SRC_ATTR = $(grid_data)
    -> AttributeFilter_3
AttributeFilter_3
    ATTR_NAME = _extension
    ATTR_VALUES = <Empty>,<Missing>,<Null>,<Unfiltered>,shp,SHP,geopackage,GEOPACKAGE,gpkg,GPKG,xml,XML,zip,ZIP
    shp -> Junction_28
    SHP -> Junction_28
    geopackage -> Junction_27
    GEOPACKAGE -> Junction_27
    gpkg -> Junction_27
    GPKG -> Junction_27
    xml -> Junction_26
    XML -> Junction_26
    zip -> FeatureReader_2 [INITIATOR]
    ZIP -> FeatureReader_2 [INITIATOR]

Bookmark: path grids
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Merge Initiator and Result
    ATTR_CONFLICT_RES = Use Result
    ATTR_IGNORE_NULLS = No
    COMBINE_GEOM = Use Result
    DATASET = $(grid_data)
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = NO
    PATH_TYPE = ANY
    PATH_USE_NON_STRING_ATTR = yes
    PATH -> AttributeCreator_14
AttributeCreator_14
    ATTR_TABLE = SET_TO _dirpath = $(grid_data)
    -> AttributeFilter_5
AttributeFilter_5
    ATTR_NAME = path_extension
    ATTR_VALUES = <Empty>,<Missing>,<Null>,<Unfiltered>,shp,SHP,geopackage,GEOPACKAGE,gpkg,GPKG,xml,XML
    shp -> Junction_6
    SHP -> Junction_6
    geopackage -> Junction_8
    GEOPACKAGE -> Junction_8
    gpkg -> Junction_8
    GPKG -> Junction_8
    xml -> Junction_5
    XML -> Junction_5

Bookmark: shp grids
Sampler_2
    RATE = 1
    SAMPLE_MODE = No
    SAMPLE_TYPE_LONG = First N Features
    SAMPLED -> FeatureReader_shp_grids [INITIATOR]
FeatureReader_shp_grids
    ATTRS_TO_EXPOSE = fme_basename fme_dataset fme_feature_type
    ATTR_ACCUM_MODE = Merge Initiator and Result
    ATTR_CONFLICT_RES = Use Result
    ATTR_IGNORE_NULLS = No
    COMBINE_GEOM = Use Result
    DATASET = @Value(_dirpath)\**\*.shp
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_SHAPEFILE_EXPOSE_FORMAT_ATTRS = fme_basename,char(50) fme_dataset,char(50) fme_feature_type,char(50)
    SHAPEFILE_TRIM_PRECEDING_SPACES = Yes
    SHAPEFILE_USE_SEARCH_ENVELOPE = NO
    <OTHER> -> AttributeCreator_19
AttributeCreator_19
    ATTR_TABLE = SET_TO is_it_grid = 1
    -> Junction_9

Bookmark: gpkg grids
Sampler_4
    RATE = 1
    SAMPLE_MODE = No
    SAMPLE_TYPE_LONG = First N Features
    SAMPLED -> FeatureReader_gpkg_grids [INITIATOR]
FeatureReader_gpkg_grids
    ATTRS_TO_EXPOSE = fme_basename fme_dataset fme_feature_type
    ATTR_ACCUM_MODE = Merge Initiator and Result
    ATTR_CONFLICT_RES = Use Result
    ATTR_IGNORE_NULLS = No
    COMBINE_GEOM = Use Result
    DATASET = @Value(_dirpath)\**\*.gpkg
    FORMAT = GEOPACKAGE
    GEOPACKAGE_ENCODE_FEATURE_TYPE_AND_ATTR_NAMES = YES
    GEOPACKAGE_ENFORCE_FOREIGN_KEY_INTEGRITY = YES
    GEOPACKAGE_EXPOSE_PRIMARY_KEY_ATTRIBUTE = NO
    GEOPACKAGE_GEOPACKAGE_EXPOSE_FORMAT_ATTRS = fme_basename,text(50) fme_dataset,text(50) fme_feature_type,text(50)
    GEOPACKAGE_OPEN_SINGLE_RASTER_AS_SUBDATASET = YES
    GEOPACKAGE_QUERY_FEATURE_TYPES_FOR_MERGE_FILTERS = Yes
    GEOPACKAGE_READER_REPLACE_INVALID_CHARS = YES
    GEOPACKAGE_READ_BOOLEANS_AS_YES_NO = YES
    GEOPACKAGE_READ_NULLS = YES
    GEOPACKAGE_USE_SEARCH_ENVELOPE = NO
    INTERACT = NONE
    OUTPUT_FEATURES_DISPLAY = Schema and Data Features
    <OTHER> -> AttributeCreator_22
AttributeCreator_22
    ATTR_TABLE = SET_TO is_it_grid = 1
    -> Junction_7

Bookmark: coordsys management. is it right?
Note: get original / coordsys from files
Note: Write custom grid to database
CoordinateSystemExtractor
    CRDSYS_ATTR = _original_coordsys
    -> Aggregator
Aggregator
    ACCUM_ATTRS_NAME = Use Attributes From One Feature
    AGGREGATE_TYPE = Homogeneous Collection (If Possible)
    COUNT_ATTR = total_asset_objects
    GROUP_BY = fme_feature_type is_it_grid fme_basename processing_start
    MODE = Geometry - Assemble One Level
    SEP = ,
    AGGREGATE -> AttributeRenamer_2
AttributeRenamer_2
    ATTR_TABLE = RENAME_SET_DEFAULT ref_asset_group > id
    MISSING_INPUT_ATTRS = REMOVE
    -> BoundingBoxReplacer
BoundingBoxReplacer
    BOXTYPE = 2D Bounding Box
    BOX -> TestFilter_4
TestFilter_4
    DEFAULT_VALUE = <UNFILTERED>
    TEST_LIST = "BOOL_OP,OR,COMPOSITE_TEST,""""""1"""""",TEST_CLAUSE,TEST @Value(is_it_grid) = 0",ASSETS,"BOOL_OP,OR,COMPOSITE_TEST,""""""1"""""",TEST_CLAUSE,TEST @Value(is_it_grid) = 1",GRID
    ASSETS -> AttributeFilter
    GRID -> AttributeFilter
Note: filter non assigned coordsys files
AttributeFilter
    ATTR_NAME = _original_coordsys
    ATTR_VALUES = <Empty>,<Missing>,<Null>,<Unfiltered>,_LL-27_0
    <EMPTY> -> NullAttributeMapper
    <UNFILTERED> -> FeatureMerger [REQUESTOR]
    _LL-27_0 -> AttributeCreator_2

Bookmark: NOT PROPERLY DEFINED LAYERS
NullAttributeMapper
    ATTRCHOICE = Selected Attributes
    ATTRLIST = _original_coordsys
    NULL_TREATMENT = Null
    SOURCE_ATTR_VAL = Null Empty "Missing (Selected Attributes Only)"
    -> AttributeCreator
AttributeCreator
    ATTR_TABLE = SET_TO issues_log = Not defined coordinate system on layer @Value(fme_feature_type)
    -> AttributeRenamer_4
AttributeCreator_2
    ATTR_TABLE = SET_TO issues_log = Not properly defined coordinate system on layer @Value(fme_feature_type)
    -> AttributeRenamer_4
AttributeRenamer_4
    ATTR_TABLE = RENAME_SET_DEFAULT id > ref_asset_group
    MISSING_INPUT_ATTRS = REMOVE
    -> UUIDGenerator_2

Bookmark: REPORTING ISSUES for asset_group
UUIDGenerator_2
    UUID_ATTR = id
    -> AttributeKeeper_6
AttributeKeeper_6
    CREATE_BULK_MODE_FEATURES = NO
    KEEP_ATTRS = date_import,id,ref_asset_group,issue_found,ref_asset_object,issues_log,process
    -> PROJReprojector_3
PROJReprojector_3
    DEST = EPSG:4326
    DEST_TAG = EPSG:4326
    INTERPOLATION_TYPE_NAME = Nearest Neighbor
    RASTER_CELL_SIZE = Preserve Cells
    RASTER_TOLERANCE = 0.0
    TRANSFORM_TYPE = Automatic Transformation
    REPROJECTED -> VariableRetriever_6

Bookmark: Custom grid, precalculate key values
Note: Create unique ID
UUIDGenerator_3
    UUID_ATTR = id
    -> AreaCalculator
Note: AreaCalculator / calculated area of custom grid in projection that is uploaded.
AreaCalculator
    AREA_ATTR = area_km2
    AREA_TYPE = Plane Area
    MULT = 1e-6
    -> PROJReprojector_4
Note: Reproject custom grid to 4326
PROJReprojector_4
    DEST = EPSG:4326
    DEST_TAG = EPSG:4326
    INTERPOLATION_TYPE_NAME = Nearest Neighbor
    RASTER_CELL_SIZE = Preserve Cells
    RASTER_TOLERANCE = 0.0
    TRANSFORM_TYPE = Automatic Transformation
    REPROJECTED -> CenterPointExtractor
Note: get lat lon centerpoint position
CenterPointExtractor
    CENTX = lon_center
    CENTY = lat_center
    EXTRACTIONMODE = CENTER
    -> BoundsExtractor
Aggregator_10
    ACCUM_ATTRS_NAME = Use Attributes From One Feature
    GROUP_BY = area_reference
    MODE = Attributes Only
    SEP = ,
    AGGREGATE -> Counter_2
Counter_2
    CNT_ATTR = level_qdgc
    DOMAIN = counter
    SCOPE = Global
    START = 1
    -> FeatureMerger_3 [SUPPLIER]
FeatureMerger_3
    ATTR_ACCUM_MODE = Merge Supplier
    ATTR_CONFLICT_RES = Use Requestor
    IGNORE_NULLS = No
    JOIN_KEYS = @Value(area_reference) @Value(area_reference) AUTO
    MERGE_TYPE = Attributes Only
    PROCESS_DUPS = NO
    REJECT_NULL_MISSING_KEYS = No
    SUPPLIERS_FIRST = No
    MERGED -> VariableRetriever_7
    UNMERGED_REQUESTOR -> VariableRetriever_7

Bookmark: Calculate cellsize_degrees for custom grid
BoundsExtractor
    XMAX = _xmax
    XMIN = _xmin
    -> AttributeCreator_5
AttributeCreator_5
    ATTR_TABLE:
      SET_TO cellsize_degrees = @Evaluate(@round(@abs(@Value(_xmax)-@Value(_xmin)),4))
      SET_TO lat_center = @Evaluate(@round(@Value(lat_center),4))
      SET_TO lon_center = @Evaluate(@round(@Value(lon_center),4))
      SET_TO area_reference = @Value(fme_feature_type)
    -> FeatureMerger_3 [REQUESTOR]
    -> Aggregator_10

Bookmark: shp.xml grids
Sampler_6
    RATE = 1
    SAMPLE_MODE = No
    SAMPLE_TYPE_LONG = First N Features
    SAMPLED -> FeatureReader_shp.xml_grids [INITIATOR]
FeatureReader_shp.xml_grids
    ATTRS_TO_EXPOSE = fme_basename fme_dataset fme_feature_type
    ATTR_ACCUM_MODE = Merge Initiator and Result
    ATTR_CONFLICT_RES = Use Result
    ATTR_IGNORE_NULLS = No
    COMBINE_GEOM = Use Result
    DATASET = @Value(_dirpath)\**\*.shp.xml
    FORMAT = XML
    INTERACT = NONE
    OUTPUT_FEATURES_DISPLAY = Schema and Data Features
    XML_CONTINUE_ON_GEOM_ERROR = no
    XML_FILE_TYPE = Feature Paths
    XML_SUPPORTED_READER_ARCHIVE_EXTENSIONS = xml.gz,gml.gz
    XML_USE_SEARCH_ENVELOPE = NO
    XML_VALIDATE_DATASET = no
    XML_VALIDATE_XFMAP = no
    XML_XFMAP_FEATURE_PATHS = metadata
    XML_XFMAP_FEATURE_PATHS_STRUCTURE:
      <structure
      separator="."
      map-empty-elements="yes"
      matched-prefix="attributes"
      matched-attributes="yes"
      cardinality="+{?}"
      except-expression=""
      structure-prefix=""
      child-position-attribute=""
      attribute-identifier=""
      ui-mode="basic"/>
    <OTHER> -> Aggregator_3

Bookmark: CLEAN ATTRIBUTES FROM METADATA
Aggregator_3
    ACCUM_ATTRS_NAME = Use Attributes From One Feature
    AGGREGATE_TYPE = Homogeneous Collection (If Possible)
    GROUP_BY = fme_basename
    MODE = Geometry - Assemble One Level
    SEP = ,
    AGGREGATE -> StringReplacer
StringReplacer
    CASE = NO
    FIND_TEXT = .shp
    NO_MATCH = _FME_NO_OP_
    REGEXP = NO
    SRC_ATTRS = fme_basename
    -> AttributeKeeper_2
AttributeKeeper_2
    CREATE_BULK_MODE_FEATURES = No
    KEEP_ATTRS = fme_dataset,Esri.CreaDate,fme_basename
    -> FeatureMerger [SUPPLIER]

Bookmark: MERGE metadata with layers create attributes for excel output
FeatureMerger
    ATTR_ACCUM_MODE = Merge Supplier
    ATTR_CONFLICT_RES = Use Requestor
    IGNORE_NULLS = No
    JOIN_KEYS = @Value(path_rootname) @Value(fme_basename) AUTO
    MERGE_TYPE = Attributes Only
    PROCESS_DUPS = NO
    REJECT_NULL_MISSING_KEYS = No
    SUPPLIERS_FIRST = No
    MERGED -> Sorter_5
    UNMERGED_REQUESTOR -> Sorter_5
Note: fist assets then grids into excel file
Sorter_5
    SORT_PARM = is_it_grid NUMERIC ASCENDING
    SORTED -> Counter
Counter
    CNT_ATTR = _count
    DOMAIN = counter
    SCOPE = Global
    START = 1
    -> AttributeCreator_3
AttributeCreator_3
    ATTR_TABLE:
      SET_TO _count_excel_row = @Evaluate(@Value(_count)+1)
      SET_TO Datasett = dataset_@Value(_count)
      SET_TO Sensitivity
      SET_TO importance_local
      SET_TO importance_global
      SET_TO importance_combined
      SET_TO susceptibility_local
      SET_TO susceptibility_global
      SET_TO susceptibility_combined
      SET_TO susceptibility_local.formula = =C@Value(_count_excel_row)*D@Value(_count_excel_row)
      SET_TO susceptibility_global.formula = =C@Value(_count_excel_row)*E@Value(_count_excel_row)
      SET_TO susceptibility_combined.formula = =C@Value(_count_excel_row)*F@Value(_count_excel_row)
      SET_TO Latest_update_date = @Value(Esri.CreaDate)
      SET_TO asset_type
      SET_TO asset_name = @Value(fme_feature_type)
      SET_TO asset_referencenumber
      SET_TO asset_date = @Value(Esri.CreaDate)
    -> NullAttributeMapper_2
NullAttributeMapper_2
    ATTRCHOICE = Selected Attributes
    ATTRLIST = fme_dataset fme_feature_type asset_referencenumber Datasett asset_name _original_coordsys asset_type Esri.CreaDate Latest_update_date _count Sensitivity asset_date fme_basename importance_combined importance_global importance_local
    NULL_TREATMENT = Null
    SOURCE_ATTR_VAL = Null Empty "Missing (Selected Attributes Only)"
    -> AttributeKeeper
AttributeKeeper
    CREATE_BULK_MODE_FEATURES = NO
    KEEP_ATTRS = fme_basename,_count,Sensitivity,Latest_update_date,asset_referencenumber,fme_dataset,asset_type,Datasett,asset_date,is_it_grid,_original_coordsys,asset_name,fme_feature_type,importance_combined,importance_global,importance_local,id,susceptibility_combined,susceptibility_combined.formula,susceptibility_global,susceptibility_global.formula,susceptibility_local,susceptibility_local.formula,_count_excel_row
    -> TestFilter

Bookmark: formula excel combo_pri
TestFilter
    DEFAULT_VALUE = NOT A GRID ASSET
    TEST_LIST = "BOOL_OP,OR,COMPOSITE_TEST,""""""1"""""",TEST_CLAUSE,CASE_INSENSITIVE_TEST @Value(is_it_grid) = 1",GRID ASSET
    GRID ASSET -> ExcelStyler
    NOT A GRID ASSET -> ExcelStyler_3
Note: fist assets then grids into excel file
Sorter_2
    SORT_PARM = is_it_grid NUMERIC ASCENDING
    SORTED -> DateTimeStamper

Bookmark: styling cells for grid and not grid assets
Note: style uneditable content
ExcelStyler_3
    BACKGROUND_COLOR = 0.929412,0.929412,0.929412
    CELL_BORDER_COLOR = 0.831373,0.831373,0.831373
    CELL_BORDER_STYLE = BORDERSTYLE_THIN
    HIDDEN = false
    LOCKED = false
    PATTERN_STYLE = FILLPATTERN_NONE
    ROW_OR_CELL = row
    ExcelStyled -> ExcelStyler_2
Note: Styled editable cells green
ExcelStyler_2
    ATTRS_TO_STYLE = Sensitivity importance_combined importance_global importance_local asset_date asset_referencenumber asset_type asset_name
    BACKGROUND_COLOR = 0.764706,1,0.792157
    CELL_BORDER_COLOR = 0.831373,0.831373,0.831373
    CELL_BORDER_STYLE = BORDERSTYLE_THIN
    ROW_OR_CELL = cell
    ExcelStyled -> Sorter_2
ExcelStyler
    BACKGROUND_COLOR = 1,0.482353,0.278431
    CELL_BORDER_COLOR = 0.831373,0.831373,0.831373
    CELL_BORDER_STYLE = BORDERSTYLE_THIN
    LOCKED = false
    PATTERN_STYLE = FILLPATTERN_NONE
    ROW_OR_CELL = row
    ExcelStyled -> Sorter_3
Note: first assets then grids into excel file
Sorter_3
    SORT_PARM = asset_name ALPHA ASCENDING
    SORTED -> Sorter_2

Bookmark: writing to project[code].tbl_asset_group
Note: Create tbl_asset group variable info
AttributeCreator_9
    ATTR_TABLE:
      SET_TO name = FME_CONDITIONAL:DEFAULT_VALUE'$(ref_user)_$(Projectname)_grid_@Value(asset_name)'BOOL_OP;OR;COMPOSITE_TEST;1;TEST @Value(is_it_grid) = 0'$(ref_user)_$(Projectname)_asset_@Value(asset_name)'FME_NUM_CONDITIONS2___
      SET_TO attributes = [
            "JOB PARAMETERS":
            {
            asset_data: '$(asset_data)',
            asset_group_name: '$(asset_group_name)',
            delete_previous_grid: '$(delete_previous_grid)',
            email: '$(Email)',
            geocode_grid: '$(geocode_grid)',
            qdgc_levels: '$(qdgc_levels_min)',
            grid_data: '$(grid_data)',
            Projectname: '$(Projectname)',
            ref_user: '$(ref_user)',
            fme_job_id: '$(FME_JOB_ID)'
            },
            "datetime":@Value(_timestamp),
            "asset_name":@Value(asset_name),
            "is_grid":@Value(is_it_grid)
            "Original_coord_sys":@Value(_original_coordsys),
            "id": @Value(id)
        ]
    -> TestFilter_11
TestFilter_11
    DEFAULT_VALUE = grid
    TEST_LIST = "BOOL_OP,OR,COMPOSITE_TEST,""""""1"""""",TEST_CLAUSE,TEST @Value(is_it_grid) = 0",asset
    asset -> AttributeRenamer_3
AttributeRenamer_3
    ATTR_TABLE = RENAME_SET_DEFAULT fme_feature_type > name_original
    MISSING_INPUT_ATTRS = REMOVE
    -> PROJReprojector_2
PROJReprojector_2
    DEST = EPSG:4326
    DEST_TAG = EPSG:4326
    INTERPOLATION_TYPE_NAME = Nearest Neighbor
    RASTER_CELL_SIZE = Preserve Cells
    RASTER_TOLERANCE = 0.0
    TRANSFORM_TYPE = Automatic Transformation
    REPROJECTED -> VariableRetriever_8

Bookmark: Check if grid exists in geocode database
Note: Check that user actually set min = min and max = max
TestFilter_2
    DEFAULT_VALUE = User set min max other way around
    TEST_LIST = "BOOL_OP,OR,COMPOSITE_TEST,""""""1"""""",TEST_CLAUSE,TEST $(qdgc_levels_max) >= $(qdgc_levels_min)",max >= min
    User set min max other way around -> AttributeCreator_16
    max >= min -> AttributeCreator_15
AttributeCreator_15
    ATTR_TABLE:
      SET_TO _MAX = $(qdgc_levels_max)
      SET_TO _MIN = $(qdgc_levels_min)
    -> FeatureReader_3 [INITIATOR]
AttributeCreator_16
    ATTR_TABLE:
      SET_TO _MIN = $(qdgc_levels_max)
      SET_TO _MAX = $(qdgc_levels_min)
    -> FeatureReader_3 [INITIATOR]
FeatureReader_3
    ATTRIBUTES = geocode.tbl_geocode_object,"id,area_reference,level_qdgc,cellsize_degrees,lon_center,lat_center,area_km2"
    ATTR_ACCUM_MODE = Merge Initiator and Result
    ATTR_CONFLICT_RES = Use Result
    ATTR_IGNORE_NULLS = No
    COMBINE_GEOM = Use Result
    DATASET = $(param_connectionstring_mesadatabase)
    FEATURETYPES = geocode.tbl_geocode_object
    FORMAT = POSTGIS
    INTERACT = ENVELOPE_INTERSECTS
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = $(param_connectionstring_mesadatabase)
    POSTGIS_QUERY_FEATURE_TYPES_FOR_MERGE_FILTERS = Yes
    POSTGIS_READ_TIME_WITH_TIMEZONE = Yes
    POSTGIS_SCHEMAS_FOR_TABLE_LISTING = geocode
    POSTGIS_USE_SEARCH_ENVELOPE = NO
    POSTGIS_USE_TRUE_POSTGIS_TYPES = yes
    WHERE = level_qdgc >= @Value(_MIN) AND level_qdgc <= @Value(_MAX)
    geocode.tbl_geocode_object -> TestFilter_7
    geocode.tbl_geocode_object -> Junction_18
    INITIATOR -> Clipper [CANDIDATE]
    INITIATOR -> FeatureMerger_5 [REQUESTOR]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Aggregator_4

Bookmark: Check that highets level requested of qdgc exists in table
TestFilter_7
    DEFAULT_VALUE = <UNFILTERED>
    TEST_LIST = "BOOL_OP,AND,COMPOSITE_TEST,""""""1"""""",TEST_CLAUSE,TEST @Value(level_qdgc) = @Value(_MAX)",__qdgc_levels_ within range
    __qdgc_levels_ within range -> Dissolver
Dissolver
    ACCUM_INPUT_ATTRS = Use Attributes From One Feature
    CLEANING_TOLERANCE = Automatic
    CONNECT_Z_MODE = First Wins
    DEAGGREGATE_INPUT = Yes
    AREA -> Clipper [CLIPPER]

Bookmark: Check if existing geocode grid covers the project area
Aggregator_4
    ACCUM_ATTRS_NAME = Drop Incoming Attributes
    AGGREGATE_TYPE = Homogeneous Collection (If Possible)
    MODE = Geometry - Assemble One Level
    SEP = ,
    AGGREGATE -> AttributeCreator_8
AttributeCreator_8
    ATTR_TABLE = SET_TO stored_in_geocode = false
    -> FeatureMerger_5 [SUPPLIER]
FeatureMerger_5
    ATTR_ACCUM_MODE = Merge Supplier
    ATTR_CONFLICT_RES = Use Requestor
    IGNORE_NULLS = No
    JOIN_KEYS = 0 0 AUTO
    MERGE_TYPE = Attributes Only
    PROCESS_DUPS = NO
    REJECT_NULL_MISSING_KEYS = No
    SUPPLIERS_FIRST = No
    MERGED -> Junction_10
    UNMERGED_REQUESTOR -> Junction_17

Bookmark: Get Grid from database
Note: Complete grid exists for area
Junction_17
    -> AttributeKeeper_4
AttributeKeeper_4
    CREATE_BULK_MODE_FEATURES = No
    -> GeometryRemover
GeometryRemover
    -> FeatureMerger_6 [SUPPLIER]
Note: GRID read from geocode
Junction_18
    -> FeatureMerger_6 [REQUESTOR]
FeatureMerger_6
    ATTR_ACCUM_MODE = Merge Supplier
    ATTR_CONFLICT_RES = Use Requestor
    IGNORE_NULLS = No
    JOIN_KEYS = 0 0 AUTO
    MERGE_TYPE = Attributes Only
    PROCESS_DUPS = NO
    REJECT_NULL_MISSING_KEYS = No
    SUPPLIERS_FIRST = No
    MERGED -> VariableRetriever_7

Bookmark: Create table group based on geocode objects
Note: FeatureWriter_geocode.tbl_geocode_object : Summary
Junction_22
    -> VariableRetriever_10
VariableRetriever_10
    SCOPE = Global
    VALUE_ATTR = p_name
    VARNAME = p_name
    -> FeatureReader_4 [INITIATOR]
FeatureReader_4
    ATTR_ACCUM_MODE = Only Use Result
    COMBINE_GEOM = Use Result
    DATASET = $(param_connectionstring_mesadatabase)
    FEATURETYPES = @Value(p_name).tbl_geocode_object
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = $(param_connectionstring_mesadatabase)
    POSTGIS_QUERY_FEATURE_TYPES_FOR_MERGE_FILTERS = Yes
    POSTGIS_READ_TIME_WITH_TIMEZONE = Yes
    POSTGIS_SCHEMAS_FOR_TABLE_LISTING = $(Projectname)
    POSTGIS_USE_SEARCH_ENVELOPE = NO
    POSTGIS_USE_TRUE_POSTGIS_TYPES = yes
    <OTHER> -> AttributeExposer
AttributeExposer
    ATTR_LIST = area_km2,area_reference,cellsize_degrees,id,lat_center,level_qdgc,lon_center,postgis_type
    -> AttributeCreator_12
AttributeCreator_12
    ATTR_TABLE = SET_TO name = @Value(area_reference)_@Value(level_qdgc)
    -> Aggregator_8
Aggregator_8
    ACCUM_ATTRS_NAME = Merge Incoming Attributes
    AGGREGATE_TYPE = Homogeneous Collection (If Possible)
    GROUP_BY = name
    MODE = Geometry - Assemble One Level
    SEP = ,
    SUM = area_km2
    AGGREGATE -> AttributeJSONPacker36_2
AttributeJSONPacker36_2
    PACKED = attributes
    -> BoundingBoxReplacer_2
BoundingBoxReplacer_2
    BOXTYPE = 2D Bounding Box
    BOX -> AttributeExposer_2
AttributeExposer_2
    ATTR_LIST = attributes
    -> UUIDGenerator_4
UUIDGenerator_4
    UUID_ATTR = id
    -> VariableRetriever_4
    -> FeatureWriter_geocode.tbl_geocode_group [geocode.tbl_geocode_group]

Bookmark: geocode
Note: geocode.tbl_geocode_group
FeatureWriter_geocode.tbl_geocode_group
    DATASET = $(param_connectionstring_mesadatabase)
    DATASET_ATTR = _dataset
    FEATURE_TYPE_LIST_ATTR = _feature_types
    FORMAT = POSTGIS
    POSTGIS_BEGIN_SQL = create schema if not exists geocode;
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = MESA 3.0
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> Junction_13

Bookmark: write system.tbl_processing log file
FeatureHolder
    -> TestFilter_5
TestFilter_5
    DEFAULT_VALUE = <UNFILTERED>
    TEST_LIST = "BOOL_OP,OR,COMPOSITE_TEST,""""""1"""""",TEST_CLAUSE,TEST processing_start ATTRIBUTE_HAS_A_VALUE """,date_import ATTRIBUTE_HAS_A_VALUE
    date_import ATTRIBUTE_HAS_A_VALUE -> AttributeKeeper_8
AttributeKeeper_8
    CREATE_BULK_MODE_FEATURES = NO
    KEEP_ATTRS = processing_start
    -> DateTimeStamper_2
DateTimeStamper_2
    DATETIME_ATTR = processing_end
    INCLUDE_OFFSET = NO
    STAMP_TYPE = datetime
    TIMEZONE = utc
    -> VariableRetriever_9
VariableRetriever_9
    SCOPE = Global
    VALUE_ATTR = p_name
    VARNAME = p_name
    -> AttributeCreator_10
AttributeCreator_10
    ATTR_TABLE:
      SET_TO id = @UUID()
      SET_TO ref_user = $(ref_user)
      SET_TO schema_name = @Value(p_name)
      SET_TO process = Staging
      SET_TO time_start = @Value(processing_start)
      SET_TO time_end = @Value(processing_end)
      SET_TO time_elapsed = @Evaluate(@Value(processing_end)-@Value(processing_start))
      SET_TO full_log_fme = $(FME_JOB_ID)
      SET_TO activity_log = [
            'JOB PARAMETERS':
            {
            asset_data: '$(asset_data)',
            asset_group_name: '$(asset_group_name)',
            delete_previous_grid: '$(delete_previous_grid)',
            email: '$(Email)',
            geocode_grid: '$(geocode_grid)',
            qdgc_levels: '$(qdgc_levels_min)',
            grid_data: '$(grid_data)',
            Projectname: '$(Projectname)',
            ref_user: '$(ref_user)',
            fme_job_id: '$(FME_JOB_ID)'
            }

        ]
    -> FeatureWriter_project_code.tbl_log [Table1]
    -> FeatureWriter_system.tbl_processing__system.tbl_log [Output]
    -> FeatureWriter_system.tbl_processing__system.tbl_log [Table1]

Bookmark: FME send email to user
ParameterFetcher_3
    ATTR_LIST = _Projectname $(Projectname)
    -> ParameterFetcher_2
ParameterFetcher_2
    ATTR_LIST = _FME_SERVER_DEST_DIR $(FME_SERVER_DEST_DIR) _FME_JOB_ID $(FME_JOB_ID)
    -> FilenamePartExtractor
FilenamePartExtractor
    FULLNAME_ATTR = _filename
    SRC_ATTR = @Value(_FME_SERVER_DEST_DIR)
    -> Emailer_results
Emailer_results
    BCC = bac43dbc.miljodir.onmicrosoft.com@emea.teams.ms
    BODY:
      <html xmlns:v="urn:schemas-microsoft-com:vml"
      xmlns:o="urn:schemas-microsoft-com:office:office"
      xmlns:w="urn:schemas-microsoft-com:office:word"
      xmlns:m="http://schemas.microsoft.com/office/2004/12/omml"
      xmlns="http://www.w3.org/TR/REC-html40">

      <head>
      <meta http-equiv=Content-Type content="text/html; charset=windows-1252">
      <meta name=ProgId content=Word.Document>
      <meta name=Generator content="Microsoft Word 15">
      <meta name=Originator content="Microsoft Word 15">
      <link rel=File-List href="System%20finished%20processing-filer/filelist.xml">
      <!--[if gte mso 9]><xml>
       <o:DocumentProperties>
        <o:Author>Roman Slobodchikov</o:Author>
        <o:LastAuthor>Roman Slobodchikov</o:LastAuthor>
        <o:Revision>1</o:Revision>
        <o:TotalTime>5</o:TotalTime>
        <o:Created>2022-12-05T13:49:00Z</o:Created>
        <o:LastSaved>2022-12-05T13:54:00Z</o:LastSaved>
        <o:Pages>1</o:Pages>
        <o:Words>89</o:Words>
        <o:Characters>509</o:Characters>
        <o:Lines>4</o:Lines>
        <o:Paragraphs>1</o:Paragraphs>
        <o:CharactersWithSpaces>597</o:CharactersWithSpaces>
        <o:Version>16.00</o:Version>
       </o:DocumentProperties>
       <o:OfficeDocumentSettings>
        <o:AllowPNG/>
       </o:OfficeDocumentSettings>
      </xml><![endif]-->
      <link rel=themeData href="System%20finished%20processing-filer/themedata.thmx">
      <link rel=colorSchemeMapping
      href="System%20finished%20processing-filer/colorschememapping.xml">
      <!--[if gte mso 9]><xml>
       <w:WordDocument>
        <w:SpellingState>Clean</w:SpellingState>
        <w:GrammarState>Clean</w:GrammarState>
        <w:TrackMoves>false</w:TrackMoves>
        <w:TrackFormatting/>
        <w:PunctuationKerning/>
        <w:ValidateAgainstSchemas/>
        <w:SaveIfXMLInvalid>false</w:SaveIfXMLInvalid>
        <w:IgnoreMixedContent>false</w:IgnoreMixedContent>
        <w:AlwaysShowPlaceholderText>false</w:AlwaysShowPlaceholderText>
        <w:DoNotPromoteQF/>
        <w:LidThemeOther>EN-GB</w:LidThemeOther>
        <w:LidThemeAsian>X-NONE</w:LidThemeAsian>
        <w:LidThemeComplexScript>X-NONE</w:LidThemeComplexScript>
        <w:Compatibility>
         <w:BreakWrappedTables/>
         <w:SnapToGridInCell/>
         <w:WrapTextWithPunct/>
         <w:UseAsianBreakRules/>
         <w:DontGrowAutofit/>
         <w:SplitPgBreakAndParaMark/>
         <w:EnableOpenTypeKerning/>
         <w:DontFlipMirrorIndents/>
         <w:OverrideTableStyleHps/>
         <w:UseFELayout/>
        </w:Compatibility>
        <m:mathPr>
         <m:mathFont m:val="Cambria Math"/>
         <m:brkBin m:val="before"/>
         <m:brkBinSub m:val="&#45;-"/>
         <m:smallFrac m:val="off"/>
         <m:dispDef/>
         <m:lMargin m:val="0"/>
         <m:rMargin m:val="0"/>
         <m:defJc m:val="centerGroup"/>
         <m:wrapIndent m:val="1440"/>
         <m:intLim m:val="subSup"/>
         <m:naryLim m:val="undOvr"/>
        </m:mathPr></w:WordDocument>
      </xml><![endif]--><!--[if gte mso 9]><xml>
       <w:LatentStyles DefLockedState="false" DefUnhideWhenUsed="false"
        DefSemiHidden="false" DefQFormat="false" DefPriority="99"
        LatentStyleCount="376">
        <w:LsdException Locked="false" Priority="0" QFormat="true" Name="Normal"/>
        <w:LsdException Locked="false" Priority="9" QFormat="true" Name="heading 1"/>
        <w:LsdException Locked="false" Priority="9" SemiHidden="true"
         UnhideWhenUsed="true" QFormat="true" Name="heading 2"/>
        <w:LsdException Locked="false" Priority="9" SemiHidden="true"
         UnhideWhenUsed="true" QFormat="true" Name="heading 3"/>
        <w:LsdException Locked="false" Priority="9" SemiHidden="true"
         UnhideWhenUsed="true" QFormat="true" Name="heading 4"/>
        <w:LsdException Locked="false" Priority="9" SemiHidden="true"
         UnhideWhenUsed="true" QFormat="true" Name="heading 5"/>
        <w:LsdException Locked="false" Priority="9" SemiHidden="true"
         UnhideWhenUsed="true" QFormat="true" Name="heading 6"/>
        <w:LsdException Locked="false" Priority="9" SemiHidden="true"
         UnhideWhenUsed="true" QFormat="true" Name="heading 7"/>
        <w:LsdException Locked="false" Priority="9" SemiHidden="true"
         UnhideWhenUsed="true" QFormat="true" Name="heading 8"/>
        <w:LsdException Locked="false" Priority="9" SemiHidden="true"
         UnhideWhenUsed="true" QFormat="true" Name="heading 9"/>
        <w:LsdException Locked="false" SemiHidden="true" UnhideWhenUsed="true"
         Name="index 1"/>
        <w:LsdException Locked="false" SemiHidden="true" UnhideWhenUsed="true"
         Name="index 2"/>
        <w:LsdException Locked="false" SemiHidden="true" UnhideWhenUsed="true"
         Name="index 3"/>
        <w:LsdException Locked="false" SemiHidden="true" UnhideWhenUsed="true"
         Name="index 4"/>
        <w:LsdException Locked="false" SemiHidden="true" UnhideWhenUsed="true"
         Name="index 5"/>
        <w:LsdException Locked="false" SemiHidden="true" UnhideWhenUsed="true"
         Name="index 6"/>
        <w:LsdException Locked="false" SemiHidden="true" UnhideWhenUsed="true"
         Name="index 7"/>
        <w:LsdException Locked="false" SemiHidden="true" UnhideWhenUsed="true"
         Name="index 8"/>
        <w:LsdException Locked="false" SemiHidden="true" UnhideWhenUsed="true"
         Name="index 9"/>
        <w:LsdException Locked="false" Priority="39" SemiHidden="true"
         UnhideWhenUsed="true" Name="toc 1"/>
        <w:LsdException Locked="false" Priority="39" SemiHidden="true"
         UnhideWhenUsed="true" Name="toc 2"/>
        <w:LsdException Locked="false" Priority="39" SemiHidden="true"
         UnhideWhenUsed="true" Name="toc 3"/>
        <w:LsdException Locked="false" Priority="39" SemiHidden="true"
         UnhideWhenUsed="true" Name="toc 4"/>
        <w:LsdException Locked="false" Priority="39" SemiHidden="true"
         UnhideWhenUsed="true" Name="toc 5"/>
        <w:LsdException Locked="false" Priority="39" SemiHidden="true"
         UnhideWhenUsed="true" Name="toc 6"/>
        <w:LsdException Locked="false" Priority="39" SemiHidden="true"
         UnhideWhenUsed="true" Name="toc 7"/>
        <w:LsdException Locked="false" Priority="39" SemiHidden="true"
         UnhideWhenUsed="true" Name="toc 8"/>
        <w:LsdException Locked="false" Priority="39" SemiHidden="true"
         UnhideWhenUsed="true" Name="toc 9"/>
        <w:LsdException Locked="false" SemiHidden="true" UnhideWhenUsed="true"
         Name="Normal Indent"/>
        <w:LsdException Locked="false" SemiHidden="true" UnhideWhenUsed="true"
         Name="footnote text"/>
        <w:LsdException Locked="false" SemiHidden="true" UnhideWhenUsed="true"
         Name="annotation text"/>
        <w:LsdException Locked="false" SemiHidden="true" UnhideWhenUsed="true"
         Name="header"/>
        <w:LsdException Locked="false" SemiHidden="true" UnhideWhenUsed="true"
         Name="footer"/>
        <w:LsdException Locked="false" SemiHidden="true" UnhideWhenUsed="true"
         Name="index heading"/>
        <w:LsdException Locked="false" Priority="35" SemiHidden="true"
         UnhideWhenUsed="true" QFormat="true" Name="caption"/>
        <w:LsdException Locked="false" SemiHidden="true" UnhideWhenUsed="true"
         Name="table of figures"/>
        <w:LsdException Locked="false" SemiHidden="true" UnhideWhenUsed="true"
         Name="envelope address"/>
        <w:LsdException Locked="false" SemiHidden="true" UnhideWhenUsed="true"
         Name="envelope return"/>
        <w:LsdException Locked="false" SemiHidden="true" UnhideWhenUsed="true"
         Name="footnote reference"/>
        <w:LsdException Locked="false" SemiHidden="true" UnhideWhenUsed="true"
         Name="annotation reference"/>
        <w:LsdException Locked="false" SemiHidden="true" UnhideWhenUsed="true"
         Name="line number"/>
        <w:LsdException Locked="false" SemiHidden="true" UnhideWhenUsed="true"
         Name="page number"/>
        <w:LsdException Locked="false" SemiHidden="true" UnhideWhenUsed="true"
         Name="endnote reference"/>
        <w:LsdException Locked="false" SemiHidden="true" UnhideWhenUsed="true"
         Name="endnote text"/>
        <w:LsdException Locked="false" SemiHidden="true" UnhideWhenUsed="true"
         Name="table of authorities"/>
        <w:LsdException Locked="false" SemiHidden="true" UnhideWhenUsed="true"
         Name="macro"/>
        <w:LsdException Locked="false" SemiHidden="true" UnhideWhenUsed="true"
         Name="toa heading"/>
        <w:LsdException Locked="false" SemiHidden="true" UnhideWhenUsed="true"
         Name="List"/>
        <w:LsdException Locked="false" SemiHidden="true" UnhideWhenUsed="true"
         Name="List Bullet"/>
        <w:LsdException Locked="false" SemiHidden="true" UnhideWhenUsed="true"
         Name="List Number"/>
        <w:LsdException Locked="false" SemiHidden="true" UnhideWhenUsed="true"
         Name="List 2"/>
        <w:LsdException Locked="false" SemiHidden="true" UnhideWhenUsed="true"
         Name="List 3"/>
        <w:LsdException Locked="false" SemiHidden="true" UnhideWhenUsed="true"
         Name="List 4"/>
        <w:LsdException Locked="false" SemiHidden="true" UnhideWhenUsed="true"
         Name="List 5"/>
        <w:LsdException Locked="false" SemiHidden="true" UnhideWhenUsed="true"
         Name="List Bullet 2"/>
        <w:LsdException Locked="false" SemiHidden="true" UnhideWhenUsed="true"
         Name="List Bullet 3"/>
        <w:LsdException Locked="false" SemiHidden="true" UnhideWhenUsed="true"
         Name="List Bullet 4"/>
        <w:LsdException Locked="false" SemiHidden="true" UnhideWhenUsed="true"
         Name="List Bullet 5"/>
        <w:LsdException Locked="false" SemiHidden="true" UnhideWhenUsed="true"
         Name="List Number 2"/>
        <w:LsdException Locked="false" SemiHidden="true" UnhideWhenUsed="true"
         Name="List Number 3"/>
        <w:LsdException Locked="false" SemiHidden="true" UnhideWhenUsed="true"
         Name="List Number 4"/>
        <w:LsdException Locked="false" SemiHidden="true" UnhideWhenUsed="true"
         Name="List Number 5"/>
        <w:LsdException Locked="false" Priority="10" QFormat="true" Name="Title"/>
        <w:LsdException Locked="false" SemiHidden="true" UnhideWhenUsed="true"
         Name="Closing"/>
        <w:LsdException Locked="false" SemiHidden="true" UnhideWhenUsed="true"
         Name="Signature"/>
        <w:LsdException Locked="false" Priority="1" SemiHidden="true"
         UnhideWhenUsed="true" Name="Default Paragraph Font"/>
        <w:LsdException Locked="false" SemiHidden="true" UnhideWhenUsed="true"
         Name="Body Text"/>
        <w:LsdException Locked="false" SemiHidden="true" UnhideWhenUsed="true"
         Name="Body Text Indent"/>
        <w:LsdException Locked="false" SemiHidden="true" UnhideWhenUsed="true"
         Name="List Continue"/>
        <w:LsdException Locked="false" SemiHidden="true" UnhideWhenUsed="true"
         Name="List Continue 2"/>
        <w:LsdException Locked="false" SemiHidden="true" UnhideWhenUsed="true"
         Name="List Continue 3"/>
        <w:LsdException Locked="false" SemiHidden="true" UnhideWhenUsed="true"
         Name="List Continue 4"/>
        <w:LsdException Locked="false" SemiHidden="true" UnhideWhenUsed="true"
         Name="List Continue 5"/>
        <w:LsdException Locked="false" SemiHidden="true" UnhideWhenUsed="true"
         Name="Message Header"/>
        <w:LsdException Locked="false" Priority="11" QFormat="true" Name="Subtitle"/>
        <w:LsdException Locked="false" SemiHidden="true" UnhideWhenUsed="true"
         Name="Salutation"/>
        <w:LsdException Locked="false" SemiHidden="true" UnhideWhenUsed="true"
         Name="Date"/>
        <w:LsdException Locked="false" SemiHidden="true" UnhideWhenUsed="true"
         Name="Body Text First Indent"/>
        <w:LsdException Locked="false" SemiHidden="true" UnhideWhenUsed="true"
         Name="Body Text First Indent 2"/>
        <w:LsdException Locked="false" SemiHidden="true" UnhideWhenUsed="true"
         Name="Note Heading"/>
        <w:LsdException Locked="false" SemiHidden="true" UnhideWhenUsed="true"
         Name="Body Text 2"/>
        <w:LsdException Locked="false" SemiHidden="true" UnhideWhenUsed="true"
         Name="Body Text 3"/>
        <w:LsdException Locked="false" SemiHidden="true" UnhideWhenUsed="true"
         Name="Body Text Indent 2"/>
        <w:LsdException Locked="false" SemiHidden="true" UnhideWhenUsed="true"
         Name="Body Text Indent 3"/>
        <w:LsdException Locked="false" SemiHidden="true" UnhideWhenUsed="true"
         Name="Block Text"/>
        <w:LsdException Locked="false" SemiHidden="true" UnhideWhenUsed="true"
         Name="Hyperlink"/>
        <w:LsdException Locked="false" SemiHidden="true" UnhideWhenUsed="true"
         Name="FollowedHyperlink"/>
        <w:LsdException Locked="false" Priority="22" QFormat="true" Name="Strong"/>
        <w:LsdException Locked="false" Priority="20" QFormat="true" Name="Emphasis"/>
        <w:LsdException Locked="false" SemiHidden="true" UnhideWhenUsed="true"
         Name="Document Map"/>
        <w:LsdException Locked="false" SemiHidden="true" UnhideWhenUsed="true"
         Name="Plain Text"/>
        <w:LsdException Locked="false" SemiHidden="true" UnhideWhenUsed="true"
         Name="E-mail Signature"/>
        <w:LsdException Locked="false" SemiHidden="true" UnhideWhenUsed="true"
         Name="HTML Top of Form"/>
        <w:LsdException Locked="false" SemiHidden="true" UnhideWhenUsed="true"
         Name="HTML Bottom of Form"/>
        <w:LsdException Locked="false" SemiHidden="true" UnhideWhenUsed="true"
         Name="Normal (Web)"/>
        <w:LsdException Locked="false" SemiHidden="true" UnhideWhenUsed="true"
         Name="HTML Acronym"/>
        <w:LsdException Locked="false" SemiHidden="true" UnhideWhenUsed="true"
         Name="HTML Address"/>
        <w:LsdException Locked="false" SemiHidden="true" UnhideWhenUsed="true"
         Name="HTML Cite"/>
        <w:LsdException Locked="false" SemiHidden="true" UnhideWhenUsed="true"
         Name="HTML Code"/>
        <w:LsdException Locked="false" SemiHidden="true" UnhideWhenUsed="true"
         Name="HTML Definition"/>
        <w:LsdException Locked="false" SemiHidden="true" UnhideWhenUsed="true"
         Name="HTML Keyboard"/>
        <w:LsdException Locked="false" SemiHidden="true" UnhideWhenUsed="true"
         Name="HTML Preformatted"/>
        <w:LsdException Locked="false" SemiHidden="true" UnhideWhenUsed="true"
         Name="HTML Sample"/>
        <w:LsdException Locked="false" SemiHidden="true" UnhideWhenUsed="true"
         Name="HTML Typewriter"/>
        <w:LsdException Locked="false" SemiHidden="true" UnhideWhenUsed="true"
         Name="HTML Variable"/>
        <w:LsdException Locked="false" SemiHidden="true" UnhideWhenUsed="true"
         Name="Normal Table"/>
        <w:LsdException Locked="false" SemiHidden="true" UnhideWhenUsed="true"
         Name="annotation subject"/>
        <w:LsdException Locked="false" SemiHidden="true" UnhideWhenUsed="true"
         Name="No List"/>
        <w:LsdException Locked="false" SemiHidden="true" UnhideWhenUsed="true"
         Name="Outline List 1"/>
        <w:LsdException Locked="false" SemiHidden="true" UnhideWhenUsed="true"
         Name="Outline List 2"/>
        <w:LsdException Locked="false" SemiHidden="true" UnhideWhenUsed="true"
         Name="Outline List 3"/>
        <w:LsdException Locked="false" SemiHidden="true" UnhideWhenUsed="true"
         Name="Table Simple 1"/>
        <w:LsdException Locked="false" SemiHidden="true" UnhideWhenUsed="true"
         Name="Table Simple 2"/>
        <w:LsdException Locked="false" SemiHidden="true" UnhideWhenUsed="true"
         Name="Table Simple 3"/>
        <w:LsdException Locked="false" SemiHidden="true" UnhideWhenUsed="true"
         Name="Table Classic 1"/>
        <w:LsdException Locked="false" SemiHidden="true" UnhideWhenUsed="true"
         Name="Table Classic 2"/>
        <w:LsdException Locked="false" SemiHidden="true" UnhideWhenUsed="true"
         Name="Table Classic 3"/>
        <w:LsdException Locked="false" SemiHidden="true" UnhideWhenUsed="true"
         Name="Table Classic 4"/>
        <w:LsdException Locked="false" SemiHidden="true" UnhideWhenUsed="true"
         Name="Table Colorful 1"/>
        <w:LsdException Locked="false" SemiHidden="true" UnhideWhenUsed="true"
         Name="Table Colorful 2"/>
        <w:LsdException Locked="false" SemiHidden="true" UnhideWhenUsed="true"
         Name="Table Colorful 3"/>
        <w:LsdException Locked="false" SemiHidden="true" UnhideWhenUsed="true"
         Name="Table Columns 1"/>
        <w:LsdException Locked="false" SemiHidden="true" UnhideWhenUsed="true"
         Name="Table Columns 2"/>
        <w:LsdException Locked="false" SemiHidden="true" UnhideWhenUsed="true"
         Name="Table Columns 3"/>
        <w:LsdException Locked="false" SemiHidden="true" UnhideWhenUsed="true"
         Name="Table Columns 4"/>
        <w:LsdException Locked="false" SemiHidden="true" UnhideWhenUsed="true"
         Name="Table Columns 5"/>
        <w:LsdException Locked="false" SemiHidden="true" UnhideWhenUsed="true"
         Name="Table Grid 1"/>
        <w:LsdException Locked="false" SemiHidden="true" UnhideWhenUsed="true"
         Name="Table Grid 2"/>
        <w:LsdException Locked="false" SemiHidden="true" UnhideWhenUsed="true"
         Name="Table Grid 3"/>
        <w:LsdException Locked="false" SemiHidden="true" UnhideWhenUsed="true"
         Name="Table Grid 4"/>
        <w:LsdException Locked="false" SemiHidden="true" UnhideWhenUsed="true"
         Name="Table Grid 5"/>
        <w:LsdException Locked="false" SemiHidden="true" UnhideWhenUsed="true"
         Name="Table Grid 6"/>
        <w:LsdException Locked="false" SemiHidden="true" UnhideWhenUsed="true"
         Name="Table Grid 7"/>
        <w:LsdException Locked="false" SemiHidden="true" UnhideWhenUsed="true"
         Name="Table Grid 8"/>
        <w:LsdException Locked="false" SemiHidden="true" UnhideWhenUsed="true"
         Name="Table List 1"/>
        <w:LsdException Locked="false" SemiHidden="true" UnhideWhenUsed="true"
         Name="Table List 2"/>
        <w:LsdException Locked="false" SemiHidden="true" UnhideWhenUsed="true"
         Name="Table List 3"/>
        <w:LsdException Locked="false" SemiHidden="true" UnhideWhenUsed="true"
         Name="Table List 4"/>
        <w:LsdException Locked="false" SemiHidden="true" UnhideWhenUsed="true"
         Name="Table List 5"/>
        <w:LsdException Locked="false" SemiHidden="true" UnhideWhenUsed="true"
         Name="Table List 6"/>
        <w:LsdException Locked="false" SemiHidden="true" UnhideWhenUsed="true"
         Name="Table List 7"/>
        <w:LsdException Locked="false" SemiHidden="true" UnhideWhenUsed="true"
         Name="Table List 8"/>
        <w:LsdException Locked="false" SemiHidden="true" UnhideWhenUsed="true"
         Name="Table 3D effects 1"/>
        <w:LsdException Locked="false" SemiHidden="true" UnhideWhenUsed="true"
         Name="Table 3D effects 2"/>
        <w:LsdException Locked="false" SemiHidden="true" UnhideWhenUsed="true"
         Name="Table 3D effects 3"/>
        <w:LsdException Locked="false" SemiHidden="true" UnhideWhenUsed="true"
         Name="Table Contemporary"/>
        <w:LsdException Locked="false" SemiHidden="true" UnhideWhenUsed="true"
         Name="Table Elegant"/>
        <w:LsdException Locked="false" SemiHidden="true" UnhideWhenUsed="true"
         Name="Table Professional"/>
        <w:LsdException Locked="false" SemiHidden="true" UnhideWhenUsed="true"
         Name="Table Subtle 1"/>
        <w:LsdException Locked="false" SemiHidden="true" UnhideWhenUsed="true"
         Name="Table Subtle 2"/>
        <w:LsdException Locked="false" SemiHidden="true" UnhideWhenUsed="true"
         Name="Table Web 1"/>
        <w:LsdException Locked="false" SemiHidden="true" UnhideWhenUsed="true"
         Name="Table Web 2"/>
        <w:LsdException Locked="false" SemiHidden="true" UnhideWhenUsed="true"
         Name="Table Web 3"/>
        <w:LsdException Locked="false" SemiHidden="true" UnhideWhenUsed="true"
         Name="Balloon Text"/>
        <w:LsdException Locked="false" Priority="39" Name="Table Grid"/>
        <w:LsdException Locked="false" SemiHidden="true" UnhideWhenUsed="true"
         Name="Table Theme"/>
        <w:LsdException Locked="false" SemiHidden="true" Name="Placeholder Text"/>
        <w:LsdException Locked="false" Priority="1" QFormat="true" Name="No Spacing"/>
        <w:LsdException Locked="false" Priority="60" Name="Light Shading"/>
        <w:LsdException Locked="false" Priority="61" Name="Light List"/>
        <w:LsdException Locked="false" Priority="62" Name="Light Grid"/>
        <w:LsdException Locked="false" Priority="63" Name="Medium Shading 1"/>
        <w:LsdException Locked="false" Priority="64" Name="Medium Shading 2"/>
        <w:LsdException Locked="false" Priority="65" Name="Medium List 1"/>
        <w:LsdException Locked="false" Priority="66" Name="Medium List 2"/>
        <w:LsdException Locked="false" Priority="67" Name="Medium Grid 1"/>
        <w:LsdException Locked="false" Priority="68" Name="Medium Grid 2"/>
        <w:LsdException Locked="false" Priority="69" Name="Medium Grid 3"/>
        <w:LsdException Locked="false" Priority="70" Name="Dark List"/>
        <w:LsdException Locked="false" Priority="71" Name="Colorful Shading"/>
        <w:LsdException Locked="false" Priority="72" Name="Colorful List"/>
        <w:LsdException Locked="false" Priority="73" Name="Colorful Grid"/>
        <w:LsdException Locked="false" Priority="60" Name="Light Shading Accent 1"/>
        <w:LsdException Locked="false" Priority="61" Name="Light List Accent 1"/>
        <w:LsdException Locked="false" Priority="62" Name="Light Grid Accent 1"/>
        <w:LsdException Locked="false" Priority="63" Name="Medium Shading 1 Accent 1"/>
        <w:LsdException Locked="false" Priority="64" Name="Medium Shading 2 Accent 1"/>
        <w:LsdException Locked="false" Priority="65" Name="Medium List 1 Accent 1"/>
        <w:LsdException Locked="false" SemiHidden="true" Name="Revision"/>
        <w:LsdException Locked="false" Priority="34" QFormat="true"
         Name="List Paragraph"/>
        <w:LsdException Locked="false" Priority="29" QFormat="true" Name="Quote"/>
        <w:LsdException Locked="false" Priority="30" QFormat="true"
         Name="Intense Quote"/>
        <w:LsdException Locked="false" Priority="66" Name="Medium List 2 Accent 1"/>
        <w:LsdException Locked="false" Priority="67" Name="Medium Grid 1 Accent 1"/>
        <w:LsdException Locked="false" Priority="68" Name="Medium Grid 2 Accent 1"/>
        <w:LsdException Locked="false" Priority="69" Name="Medium Grid 3 Accent 1"/>
        <w:LsdException Locked="false" Priority="70" Name="Dark List Accent 1"/>
        <w:LsdException Locked="false" Priority="71" Name="Colorful Shading Accent 1"/>
        <w:LsdException Locked="false" Priority="72" Name="Colorful List Accent 1"/>
        <w:LsdException Locked="false" Priority="73" Name="Colorful Grid Accent 1"/>
        <w:LsdException Locked="false" Priority="60" Name="Light Shading Accent 2"/>
        <w:LsdException Locked="false" Priority="61" Name="Light List Accent 2"/>
        <w:LsdException Locked="false" Priority="62" Name="Light Grid Accent 2"/>
        <w:LsdException Locked="false" Priority="63" Name="Medium Shading 1 Accent 2"/>
        <w:LsdException Locked="false" Priority="64" Name="Medium Shading 2 Accent 2"/>
        <w:LsdException Locked="false" Priority="65" Name="Medium List 1 Accent 2"/>
        <w:LsdException Locked="false" Priority="66" Name="Medium List 2 Accent 2"/>
        <w:LsdException Locked="false" Priority="67" Name="Medium Grid 1 Accent 2"/>
        <w:LsdException Locked="false" Priority="68" Name="Medium Grid 2 Accent 2"/>
        <w:LsdException Locked="false" Priority="69" Name="Medium Grid 3 Accent 2"/>
        <w:LsdException Locked="false" Priority="70" Name="Dark List Accent 2"/>
        <w:LsdException Locked="false" Priority="71" Name="Colorful Shading Accent 2"/>
        <w:LsdException Locked="false" Priority="72" Name="Colorful List Accent 2"/>
        <w:LsdException Locked="false" Priority="73" Name="Colorful Grid Accent 2"/>
        <w:LsdException Locked="false" Priority="60" Name="Light Shading Accent 3"/>
        <w:LsdException Locked="false" Priority="61" Name="Light List Accent 3"/>
        <w:LsdException Locked="false" Priority="62" Name="Light Grid Accent 3"/>
        <w:LsdException Locked="false" Priority="63" Name="Medium Shading 1 Accent 3"/>
        <w:LsdException Locked="false" Priority="64" Name="Medium Shading 2 Accent 3"/>
        <w:LsdException Locked="false" Priority="65" Name="Medium List 1 Accent 3"/>
        <w:LsdException Locked="false" Priority="66" Name="Medium List 2 Accent 3"/>
        <w:LsdException Locked="false" Priority="67" Name="Medium Grid 1 Accent 3"/>
        <w:LsdException Locked="false" Priority="68" Name="Medium Grid 2 Accent 3"/>
        <w:LsdException Locked="false" Priority="69" Name="Medium Grid 3 Accent 3"/>
        <w:LsdException Locked="false" Priority="70" Name="Dark List Accent 3"/>
        <w:LsdException Locked="false" Priority="71" Name="Colorful Shading Accent 3"/>
        <w:LsdException Locked="false" Priority="72" Name="Colorful List Accent 3"/>
        <w:LsdException Locked="false" Priority="73" Name="Colorful Grid Accent 3"/>
        <w:LsdException Locked="false" Priority="60" Name="Light Shading Accent 4"/>
        <w:LsdException Locked="false" Priority="61" Name="Light List Accent 4"/>
        <w:LsdException Locked="false" Priority="62" Name="Light Grid Accent 4"/>
        <w:LsdException Locked="false" Priority="63" Name="Medium Shading 1 Accent 4"/>
        <w:LsdException Locked="false" Priority="64" Name="Medium Shading 2 Accent 4"/>
        <w:LsdException Locked="false" Priority="65" Name="Medium List 1 Accent 4"/>
        <w:LsdException Locked="false" Priority="66" Name="Medium List 2 Accent 4"/>
        <w:LsdException Locked="false" Priority="67" Name="Medium Grid 1 Accent 4"/>
        <w:LsdException Locked="false" Priority="68" Name="Medium Grid 2 Accent 4"/>
        <w:LsdException Locked="false" Priority="69" Name="Medium Grid 3 Accent 4"/>
        <w:LsdException Locked="false" Priority="70" Name="Dark List Accent 4"/>
        <w:LsdException Locked="false" Priority="71" Name="Colorful Shading Accent 4"/>
        <w:LsdException Locked="false" Priority="72" Name="Colorful List Accent 4"/>
        <w:LsdException Locked="false" Priority="73" Name="Colorful Grid Accent 4"/>
        <w:LsdException Locked="false" Priority="60" Name="Light Shading Accent 5"/>
        <w:LsdException Locked="false" Priority="61" Name="Light List Accent 5"/>
        <w:LsdException Locked="false" Priority="62" Name="Light Grid Accent 5"/>
        <w:LsdException Locked="false" Priority="63" Name="Medium Shading 1 Accent 5"/>
        <w:LsdException Locked="false" Priority="64" Name="Medium Shading 2 Accent 5"/>
        <w:LsdException Locked="false" Priority="65" Name="Medium List 1 Accent 5"/>
        <w:LsdException Locked="false" Priority="66" Name="Medium List 2 Accent 5"/>
        <w:LsdException Locked="false" Priority="67" Name="Medium Grid 1 Accent 5"/>
        <w:LsdException Locked="false" Priority="68" Name="Medium Grid 2 Accent 5"/>
        <w:LsdException Locked="false" Priority="69" Name="Medium Grid 3 Accent 5"/>
        <w:LsdException Locked="false" Priority="70" Name="Dark List Accent 5"/>
        <w:LsdException Locked="false" Priority="71" Name="Colorful Shading Accent 5"/>
        <w:LsdException Locked="false" Priority="72" Name="Colorful List Accent 5"/>
        <w:LsdException Locked="false" Priority="73" Name="Colorful Grid Accent 5"/>
        <w:LsdException Locked="false" Priority="60" Name="Light Shading Accent 6"/>
        <w:LsdException Locked="false" Priority="61" Name="Light List Accent 6"/>
        <w:LsdException Locked="false" Priority="62" Name="Light Grid Accent 6"/>
        <w:LsdException Locked="false" Priority="63" Name="Medium Shading 1 Accent 6"/>
        <w:LsdException Locked="false" Priority="64" Name="Medium Shading 2 Accent 6"/>
        <w:LsdException Locked="false" Priority="65" Name="Medium List 1 Accent 6"/>
        <w:LsdException Locked="false" Priority="66" Name="Medium List 2 Accent 6"/>
        <w:LsdException Locked="false" Priority="67" Name="Medium Grid 1 Accent 6"/>
        <w:LsdException Locked="false" Priority="68" Name="Medium Grid 2 Accent 6"/>
        <w:LsdException Locked="false" Priority="69" Name="Medium Grid 3 Accent 6"/>
        <w:LsdException Locked="false" Priority="70" Name="Dark List Accent 6"/>
        <w:LsdException Locked="false" Priority="71" Name="Colorful Shading Accent 6"/>
        <w:LsdException Locked="false" Priority="72" Name="Colorful List Accent 6"/>
        <w:LsdException Locked="false" Priority="73" Name="Colorful Grid Accent 6"/>
        <w:LsdException Locked="false" Priority="19" QFormat="true"
         Name="Subtle Emphasis"/>
        <w:LsdException Locked="false" Priority="21" QFormat="true"
         Name="Intense Emphasis"/>
        <w:LsdException Locked="false" Priority="31" QFormat="true"
         Name="Subtle Reference"/>
        <w:LsdException Locked="false" Priority="32" QFormat="true"
         Name="Intense Reference"/>
        <w:LsdException Locked="false" Priority="33" QFormat="true" Name="Book Title"/>
        <w:LsdException Locked="false" Priority="37" SemiHidden="true"
         UnhideWhenUsed="true" Name="Bibliography"/>
        <w:LsdException Locked="false" Priority="39" SemiHidden="true"
         UnhideWhenUsed="true" QFormat="true" Name="TOC Heading"/>
        <w:LsdException Locked="false" Priority="41" Name="Plain Table 1"/>
        <w:LsdException Locked="false" Priority="42" Name="Plain Table 2"/>
        <w:LsdException Locked="false" Priority="43" Name="Plain Table 3"/>
        <w:LsdException Locked="false" Priority="44" Name="Plain Table 4"/>
        <w:LsdException Locked="false" Priority="45" Name="Plain Table 5"/>
        <w:LsdException Locked="false" Priority="40" Name="Grid Table Light"/>
        <w:LsdException Locked="false" Priority="46" Name="Grid Table 1 Light"/>
        <w:LsdException Locked="false" Priority="47" Name="Grid Table 2"/>
        <w:LsdException Locked="false" Priority="48" Name="Grid Table 3"/>
        <w:LsdException Locked="false" Priority="49" Name="Grid Table 4"/>
        <w:LsdException Locked="false" Priority="50" Name="Grid Table 5 Dark"/>
        <w:LsdException Locked="false" Priority="51" Name="Grid Table 6 Colorful"/>
        <w:LsdException Locked="false" Priority="52" Name="Grid Table 7 Colorful"/>
        <w:LsdException Locked="false" Priority="46"
         Name="Grid Table 1 Light Accent 1"/>
        <w:LsdException Locked="false" Priority="47" Name="Grid Table 2 Accent 1"/>
        <w:LsdException Locked="false" Priority="48" Name="Grid Table 3 Accent 1"/>
        <w:LsdException Locked="false" Priority="49" Name="Grid Table 4 Accent 1"/>
        <w:LsdException Locked="false" Priority="50" Name="Grid Table 5 Dark Accent 1"/>
        <w:LsdException Locked="false" Priority="51"
         Name="Grid Table 6 Colorful Accent 1"/>
        <w:LsdException Locked="false" Priority="52"
         Name="Grid Table 7 Colorful Accent 1"/>
        <w:LsdException Locked="false" Priority="46"
         Name="Grid Table 1 Light Accent 2"/>
        <w:LsdException Locked="false" Priority="47" Name="Grid Table 2 Accent 2"/>
        <w:LsdException Locked="false" Priority="48" Name="Grid Table 3 Accent 2"/>
        <w:LsdException Locked="false" Priority="49" Name="Grid Table 4 Accent 2"/>
        <w:LsdException Locked="false" Priority="50" Name="Grid Table 5 Dark Accent 2"/>
        <w:LsdException Locked="false" Priority="51"
         Name="Grid Table 6 Colorful Accent 2"/>
        <w:LsdException Locked="false" Priority="52"
         Name="Grid Table 7 Colorful Accent 2"/>
        <w:LsdException Locked="false" Priority="46"
         Name="Grid Table 1 Light Accent 3"/>
        <w:LsdException Locked="false" Priority="47" Name="Grid Table 2 Accent 3"/>
        <w:LsdException Locked="false" Priority="48" Name="Grid Table 3 Accent 3"/>
        <w:LsdException Locked="false" Priority="49" Name="Grid Table 4 Accent 3"/>
        <w:LsdException Locked="false" Priority="50" Name="Grid Table 5 Dark Accent 3"/>
        <w:LsdException Locked="false" Priority="51"
         Name="Grid Table 6 Colorful Accent 3"/>
        <w:LsdException Locked="false" Priority="52"
         Name="Grid Table 7 Colorful Accent 3"/>
        <w:LsdException Locked="false" Priority="46"
         Name="Grid Table 1 Light Accent 4"/>
        <w:LsdException Locked="false" Priority="47" Name="Grid Table 2 Accent 4"/>
        <w:LsdException Locked="false" Priority="48" Name="Grid Table 3 Accent 4"/>
        <w:LsdException Locked="false" Priority="49" Name="Grid Table 4 Accent 4"/>
        <w:LsdException Locked="false" Priority="50" Name="Grid Table 5 Dark Accent 4"/>
        <w:LsdException Locked="false" Priority="51"
         Name="Grid Table 6 Colorful Accent 4"/>
        <w:LsdException Locked="false" Priority="52"
         Name="Grid Table 7 Colorful Accent 4"/>
        <w:LsdException Locked="false" Priority="46"
         Name="Grid Table 1 Light Accent 5"/>
        <w:LsdException Locked="false" Priority="47" Name="Grid Table 2 Accent 5"/>
        <w:LsdException Locked="false" Priority="48" Name="Grid Table 3 Accent 5"/>
        <w:LsdException Locked="false" Priority="49" Name="Grid Table 4 Accent 5"/>
        <w:LsdException Locked="false" Priority="50" Name="Grid Table 5 Dark Accent 5"/>
        <w:LsdException Locked="false" Priority="51"
         Name="Grid Table 6 Colorful Accent 5"/>
        <w:LsdException Locked="false" Priority="52"
         Name="Grid Table 7 Colorful Accent 5"/>
        <w:LsdException Locked="false" Priority="46"
         Name="Grid Table 1 Light Accent 6"/>
        <w:LsdException Locked="false" Priority="47" Name="Grid Table 2 Accent 6"/>
        <w:LsdException Locked="false" Priority="48" Name="Grid Table 3 Accent 6"/>
        <w:LsdException Locked="false" Priority="49" Name="Grid Table 4 Accent 6"/>
        <w:LsdException Locked="false" Priority="50" Name="Grid Table 5 Dark Accent 6"/>
        <w:LsdException Locked="false" Priority="51"
         Name="Grid Table 6 Colorful Accent 6"/>
        <w:LsdException Locked="false" Priority="52"
         Name="Grid Table 7 Colorful Accent 6"/>
        <w:LsdException Locked="false" Priority="46" Name="List Table 1 Light"/>
        <w:LsdException Locked="false" Priority="47" Name="List Table 2"/>
        <w:LsdException Locked="false" Priority="48" Name="List Table 3"/>
        <w:LsdException Locked="false" Priority="49" Name="List Table 4"/>
        <w:LsdException Locked="false" Priority="50" Name="List Table 5 Dark"/>
        <w:LsdException Locked="false" Priority="51" Name="List Table 6 Colorful"/>
        <w:LsdException Locked="false" Priority="52" Name="List Table 7 Colorful"/>
        <w:LsdException Locked="false" Priority="46"
         Name="List Table 1 Light Accent 1"/>
        <w:LsdException Locked="false" Priority="47" Name="List Table 2 Accent 1"/>
        <w:LsdException Locked="false" Priority="48" Name="List Table 3 Accent 1"/>
        <w:LsdException Locked="false" Priority="49" Name="List Table 4 Accent 1"/>
        <w:LsdException Locked="false" Priority="50" Name="List Table 5 Dark Accent 1"/>
        <w:LsdException Locked="false" Priority="51"
         Name="List Table 6 Colorful Accent 1"/>
        <w:LsdException Locked="false" Priority="52"
         Name="List Table 7 Colorful Accent 1"/>
        <w:LsdException Locked="false" Priority="46"
         Name="List Table 1 Light Accent 2"/>
        <w:LsdException Locked="false" Priority="47" Name="List Table 2 Accent 2"/>
        <w:LsdException Locked="false" Priority="48" Name="List Table 3 Accent 2"/>
        <w:LsdException Locked="false" Priority="49" Name="List Table 4 Accent 2"/>
        <w:LsdException Locked="false" Priority="50" Name="List Table 5 Dark Accent 2"/>
        <w:LsdException Locked="false" Priority="51"
         Name="List Table 6 Colorful Accent 2"/>
        <w:LsdException Locked="false" Priority="52"
         Name="List Table 7 Colorful Accent 2"/>
        <w:LsdException Locked="false" Priority="46"
         Name="List Table 1 Light Accent 3"/>
        <w:LsdException Locked="false" Priority="47" Name="List Table 2 Accent 3"/>
        <w:LsdException Locked="false" Priority="48" Name="List Table 3 Accent 3"/>
        <w:LsdException Locked="false" Priority="49" Name="List Table 4 Accent 3"/>
        <w:LsdException Locked="false" Priority="50" Name="List Table 5 Dark Accent 3"/>
        <w:LsdException Locked="false" Priority="51"
         Name="List Table 6 Colorful Accent 3"/>
        <w:LsdException Locked="false" Priority="52"
         Name="List Table 7 Colorful Accent 3"/>
        <w:LsdException Locked="false" Priority="46"
         Name="List Table 1 Light Accent 4"/>
        <w:LsdException Locked="false" Priority="47" Name="List Table 2 Accent 4"/>
        <w:LsdException Locked="false" Priority="48" Name="List Table 3 Accent 4"/>
        <w:LsdException Locked="false" Priority="49" Name="List Table 4 Accent 4"/>
        <w:LsdException Locked="false" Priority="50" Name="List Table 5 Dark Accent 4"/>
        <w:LsdException Locked="false" Priority="51"
         Name="List Table 6 Colorful Accent 4"/>
        <w:LsdException Locked="false" Priority="52"
         Name="List Table 7 Colorful Accent 4"/>
        <w:LsdException Locked="false" Priority="46"
         Name="List Table 1 Light Accent 5"/>
        <w:LsdException Locked="false" Priority="47" Name="List Table 2 Accent 5"/>
        <w:LsdException Locked="false" Priority="48" Name="List Table 3 Accent 5"/>
        <w:LsdException Locked="false" Priority="49" Name="List Table 4 Accent 5"/>
        <w:LsdException Locked="false" Priority="50" Name="List Table 5 Dark Accent 5"/>
        <w:LsdException Locked="false" Priority="51"
         Name="List Table 6 Colorful Accent 5"/>
        <w:LsdException Locked="false" Priority="52"
         Name="List Table 7 Colorful Accent 5"/>
        <w:LsdException Locked="false" Priority="46"
         Name="List Table 1 Light Accent 6"/>
        <w:LsdException Locked="false" Priority="47" Name="List Table 2 Accent 6"/>
        <w:LsdException Locked="false" Priority="48" Name="List Table 3 Accent 6"/>
        <w:LsdException Locked="false" Priority="49" Name="List Table 4 Accent 6"/>
        <w:LsdException Locked="false" Priority="50" Name="List Table 5 Dark Accent 6"/>
        <w:LsdException Locked="false" Priority="51"
         Name="List Table 6 Colorful Accent 6"/>
        <w:LsdException Locked="false" Priority="52"
         Name="List Table 7 Colorful Accent 6"/>
        <w:LsdException Locked="false" SemiHidden="true" UnhideWhenUsed="true"
         Name="Mention"/>
        <w:LsdException Locked="false" SemiHidden="true" UnhideWhenUsed="true"
         Name="Smart Hyperlink"/>
        <w:LsdException Locked="false" SemiHidden="true" UnhideWhenUsed="true"
         Name="Hashtag"/>
        <w:LsdException Locked="false" SemiHidden="true" UnhideWhenUsed="true"
         Name="Unresolved Mention"/>
        <w:LsdException Locked="false" SemiHidden="true" UnhideWhenUsed="true"
         Name="Smart Link"/>
       </w:LatentStyles>
      </xml><![endif]-->
      <style>
      <!--
       /* Font Definitions */
       @font-face
      	{font-family:"Cambria Math";
      	panose-1:2 4 5 3 5 4 6 3 2 4;
      	mso-font-charset:0;
      	mso-generic-font-family:roman;
      	mso-font-pitch:variable;
      	mso-font-signature:3 0 0 0 1 0;}
      @font-face
      	{font-family:Calibri;
      	panose-1:2 15 5 2 2 2 4 3 2 4;
      	mso-font-charset:0;
      	mso-generic-font-family:swiss;
      	mso-font-pitch:variable;
      	mso-font-signature:-469750017 -1040178053 9 0 511 0;}
      @font-face
      	{font-family:"Calibri Light";
      	panose-1:2 15 3 2 2 2 4 3 2 4;
      	mso-font-charset:0;
      	mso-generic-font-family:swiss;
      	mso-font-pitch:variable;
      	mso-font-signature:-469750017 -1040178053 9 0 511 0;}
       /* Style Definitions */
       p.MsoNormal, li.MsoNormal, div.MsoNormal
      	{mso-style-unhide:no;
      	mso-style-qformat:yes;
      	mso-style-parent:"";
      	margin-top:0cm;
      	margin-right:0cm;
      	margin-bottom:8.0pt;
      	margin-left:0cm;
      	line-height:115%;
      	mso-pagination:widow-orphan;
      	font-size:10.5pt;
      	font-family:"Calibri",sans-serif;
      	mso-ascii-font-family:Calibri;
      	mso-ascii-theme-font:minor-latin;
      	mso-fareast-font-family:"Times New Roman";
      	mso-fareast-theme-font:minor-fareast;
      	mso-hansi-font-family:Calibri;
      	mso-hansi-theme-font:minor-latin;
      	mso-bidi-font-family:"Times New Roman";
      	mso-bidi-theme-font:minor-bidi;
      	mso-fareast-language:EN-US;}
      h1
      	{mso-style-priority:9;
      	mso-style-unhide:no;
      	mso-style-qformat:yes;
      	mso-style-link:"Overskrift 1 Tegn";
      	mso-style-next:Normal;
      	margin-top:18.0pt;
      	margin-right:0cm;
      	margin-bottom:6.0pt;
      	margin-left:0cm;
      	mso-pagination:widow-orphan lines-together;
      	page-break-after:avoid;
      	mso-outline-level:1;
      	border:none;
      	mso-border-bottom-alt:solid #ED7D31 .5pt;
      	mso-border-bottom-themecolor:accent2;
      	padding:0cm;
      	mso-padding-alt:0cm 0cm 2.0pt 0cm;
      	font-size:20.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#262626;
      	mso-themecolor:text1;
      	mso-themetint:217;
      	mso-font-kerning:0pt;
      	mso-fareast-language:EN-US;
      	font-weight:normal;}
      h2
      	{mso-style-noshow:yes;
      	mso-style-priority:9;
      	mso-style-qformat:yes;
      	mso-style-link:"Overskrift 2 Tegn";
      	mso-style-next:Normal;
      	margin-top:6.0pt;
      	margin-right:0cm;
      	margin-bottom:0cm;
      	margin-left:0cm;
      	mso-pagination:widow-orphan lines-together;
      	page-break-after:avoid;
      	mso-outline-level:2;
      	font-size:18.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#ED7D31;
      	mso-themecolor:accent2;
      	mso-fareast-language:EN-US;
      	font-weight:normal;}
      h3
      	{mso-style-noshow:yes;
      	mso-style-priority:9;
      	mso-style-qformat:yes;
      	mso-style-link:"Overskrift 3 Tegn";
      	mso-style-next:Normal;
      	margin-top:4.0pt;
      	margin-right:0cm;
      	margin-bottom:0cm;
      	margin-left:0cm;
      	mso-pagination:widow-orphan lines-together;
      	page-break-after:avoid;
      	mso-outline-level:3;
      	font-size:16.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#C45911;
      	mso-themecolor:accent2;
      	mso-themeshade:191;
      	mso-fareast-language:EN-US;
      	font-weight:normal;}
      h4
      	{mso-style-noshow:yes;
      	mso-style-priority:9;
      	mso-style-qformat:yes;
      	mso-style-link:"Overskrift 4 Tegn";
      	mso-style-next:Normal;
      	margin-top:4.0pt;
      	margin-right:0cm;
      	margin-bottom:0cm;
      	margin-left:0cm;
      	mso-pagination:widow-orphan lines-together;
      	page-break-after:avoid;
      	mso-outline-level:4;
      	font-size:14.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	mso-fareast-language:EN-US;
      	font-weight:normal;
      	font-style:italic;}
      h5
      	{mso-style-noshow:yes;
      	mso-style-priority:9;
      	mso-style-qformat:yes;
      	mso-style-link:"Overskrift 5 Tegn";
      	mso-style-next:Normal;
      	margin-top:4.0pt;
      	margin-right:0cm;
      	margin-bottom:0cm;
      	margin-left:0cm;
      	mso-pagination:widow-orphan lines-together;
      	page-break-after:avoid;
      	mso-outline-level:5;
      	font-size:12.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#C45911;
      	mso-themecolor:accent2;
      	mso-themeshade:191;
      	mso-fareast-language:EN-US;
      	font-weight:normal;}
      h6
      	{mso-style-noshow:yes;
      	mso-style-priority:9;
      	mso-style-qformat:yes;
      	mso-style-link:"Overskrift 6 Tegn";
      	mso-style-next:Normal;
      	margin-top:4.0pt;
      	margin-right:0cm;
      	margin-bottom:0cm;
      	margin-left:0cm;
      	mso-pagination:widow-orphan lines-together;
      	page-break-after:avoid;
      	mso-outline-level:6;
      	font-size:12.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	mso-fareast-language:EN-US;
      	font-weight:normal;
      	font-style:italic;}
      p.MsoHeading7, li.MsoHeading7, div.MsoHeading7
      	{mso-style-noshow:yes;
      	mso-style-priority:9;
      	mso-style-qformat:yes;
      	mso-style-link:"Overskrift 7 Tegn";
      	mso-style-next:Normal;
      	margin-top:4.0pt;
      	margin-right:0cm;
      	margin-bottom:0cm;
      	margin-left:0cm;
      	mso-pagination:widow-orphan lines-together;
      	page-break-after:avoid;
      	mso-outline-level:7;
      	font-size:11.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	mso-fareast-language:EN-US;
      	font-weight:bold;}
      p.MsoHeading8, li.MsoHeading8, div.MsoHeading8
      	{mso-style-noshow:yes;
      	mso-style-priority:9;
      	mso-style-qformat:yes;
      	mso-style-link:"Overskrift 8 Tegn";
      	mso-style-next:Normal;
      	margin-top:4.0pt;
      	margin-right:0cm;
      	margin-bottom:0cm;
      	margin-left:0cm;
      	mso-pagination:widow-orphan lines-together;
      	page-break-after:avoid;
      	mso-outline-level:8;
      	font-size:11.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	mso-fareast-language:EN-US;}
      p.MsoHeading9, li.MsoHeading9, div.MsoHeading9
      	{mso-style-noshow:yes;
      	mso-style-priority:9;
      	mso-style-qformat:yes;
      	mso-style-link:"Overskrift 9 Tegn";
      	mso-style-next:Normal;
      	margin-top:4.0pt;
      	margin-right:0cm;
      	margin-bottom:0cm;
      	margin-left:0cm;
      	mso-pagination:widow-orphan lines-together;
      	page-break-after:avoid;
      	mso-outline-level:9;
      	font-size:11.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	mso-fareast-language:EN-US;
      	font-style:italic;}
      p.MsoCaption, li.MsoCaption, div.MsoCaption
      	{mso-style-noshow:yes;
      	mso-style-priority:35;
      	mso-style-qformat:yes;
      	mso-style-next:Normal;
      	margin-top:0cm;
      	margin-right:0cm;
      	margin-bottom:8.0pt;
      	margin-left:0cm;
      	mso-pagination:widow-orphan;
      	font-size:8.0pt;
      	font-family:"Calibri",sans-serif;
      	mso-ascii-font-family:Calibri;
      	mso-ascii-theme-font:minor-latin;
      	mso-fareast-font-family:"Times New Roman";
      	mso-fareast-theme-font:minor-fareast;
      	mso-hansi-font-family:Calibri;
      	mso-hansi-theme-font:minor-latin;
      	mso-bidi-font-family:"Times New Roman";
      	mso-bidi-theme-font:minor-bidi;
      	color:#404040;
      	mso-themecolor:text1;
      	mso-themetint:191;
      	mso-fareast-language:EN-US;
      	font-weight:bold;}
      p.MsoTitle, li.MsoTitle, div.MsoTitle
      	{mso-style-priority:10;
      	mso-style-unhide:no;
      	mso-style-qformat:yes;
      	mso-style-link:"Tittel Tegn";
      	mso-style-next:Normal;
      	margin:0cm;
      	mso-add-space:auto;
      	mso-pagination:widow-orphan;
      	font-size:48.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#262626;
      	mso-themecolor:text1;
      	mso-themetint:217;
      	mso-fareast-language:EN-US;}
      p.MsoTitleCxSpFirst, li.MsoTitleCxSpFirst, div.MsoTitleCxSpFirst
      	{mso-style-priority:10;
      	mso-style-unhide:no;
      	mso-style-qformat:yes;
      	mso-style-link:"Tittel Tegn";
      	mso-style-next:Normal;
      	mso-style-type:export-only;
      	margin:0cm;
      	mso-add-space:auto;
      	mso-pagination:widow-orphan;
      	font-size:48.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#262626;
      	mso-themecolor:text1;
      	mso-themetint:217;
      	mso-fareast-language:EN-US;}
      p.MsoTitleCxSpMiddle, li.MsoTitleCxSpMiddle, div.MsoTitleCxSpMiddle
      	{mso-style-priority:10;
      	mso-style-unhide:no;
      	mso-style-qformat:yes;
      	mso-style-link:"Tittel Tegn";
      	mso-style-next:Normal;
      	mso-style-type:export-only;
      	margin:0cm;
      	mso-add-space:auto;
      	mso-pagination:widow-orphan;
      	font-size:48.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#262626;
      	mso-themecolor:text1;
      	mso-themetint:217;
      	mso-fareast-language:EN-US;}
      p.MsoTitleCxSpLast, li.MsoTitleCxSpLast, div.MsoTitleCxSpLast
      	{mso-style-priority:10;
      	mso-style-unhide:no;
      	mso-style-qformat:yes;
      	mso-style-link:"Tittel Tegn";
      	mso-style-next:Normal;
      	mso-style-type:export-only;
      	margin:0cm;
      	mso-add-space:auto;
      	mso-pagination:widow-orphan;
      	font-size:48.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#262626;
      	mso-themecolor:text1;
      	mso-themetint:217;
      	mso-fareast-language:EN-US;}
      p.MsoSubtitle, li.MsoSubtitle, div.MsoSubtitle
      	{mso-style-priority:11;
      	mso-style-unhide:no;
      	mso-style-qformat:yes;
      	mso-style-link:"Undertittel Tegn";
      	mso-style-next:Normal;
      	margin-top:0cm;
      	margin-right:0cm;
      	margin-bottom:12.0pt;
      	margin-left:0cm;
      	line-height:115%;
      	mso-pagination:widow-orphan;
      	font-size:14.0pt;
      	font-family:"Calibri",sans-serif;
      	mso-ascii-font-family:Calibri;
      	mso-ascii-theme-font:minor-latin;
      	mso-fareast-font-family:"Times New Roman";
      	mso-fareast-theme-font:minor-fareast;
      	mso-hansi-font-family:Calibri;
      	mso-hansi-theme-font:minor-latin;
      	mso-bidi-font-family:"Times New Roman";
      	mso-bidi-theme-font:minor-bidi;
      	color:#404040;
      	mso-themecolor:text1;
      	mso-themetint:191;
      	text-transform:uppercase;
      	letter-spacing:1.0pt;
      	mso-fareast-language:EN-US;}
      a:link, span.MsoHyperlink
      	{mso-style-priority:99;
      	color:#0563C1;
      	mso-themecolor:hyperlink;
      	text-decoration:underline;
      	text-underline:single;}
      a:visited, span.MsoHyperlinkFollowed
      	{mso-style-noshow:yes;
      	mso-style-priority:99;
      	color:#954F72;
      	mso-themecolor:followedhyperlink;
      	text-decoration:underline;
      	text-underline:single;}
      em
      	{mso-style-priority:20;
      	mso-style-unhide:no;
      	mso-style-qformat:yes;
      	color:black;
      	mso-themecolor:text1;}
      p.MsoNoSpacing, li.MsoNoSpacing, div.MsoNoSpacing
      	{mso-style-priority:1;
      	mso-style-unhide:no;
      	mso-style-qformat:yes;
      	mso-style-parent:"";
      	margin:0cm;
      	mso-pagination:widow-orphan;
      	font-size:10.5pt;
      	font-family:"Calibri",sans-serif;
      	mso-ascii-font-family:Calibri;
      	mso-ascii-theme-font:minor-latin;
      	mso-fareast-font-family:"Times New Roman";
      	mso-fareast-theme-font:minor-fareast;
      	mso-hansi-font-family:Calibri;
      	mso-hansi-theme-font:minor-latin;
      	mso-bidi-font-family:"Times New Roman";
      	mso-bidi-theme-font:minor-bidi;
      	mso-fareast-language:EN-US;}
      p.MsoQuote, li.MsoQuote, div.MsoQuote
      	{mso-style-priority:29;
      	mso-style-unhide:no;
      	mso-style-qformat:yes;
      	mso-style-link:"Sitat Tegn";
      	mso-style-next:Normal;
      	margin-top:8.0pt;
      	margin-right:36.0pt;
      	margin-bottom:8.0pt;
      	margin-left:36.0pt;
      	text-align:center;
      	line-height:115%;
      	mso-pagination:widow-orphan;
      	font-size:12.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:black;
      	mso-themecolor:text1;
      	mso-fareast-language:EN-US;}
      p.MsoIntenseQuote, li.MsoIntenseQuote, div.MsoIntenseQuote
      	{mso-style-priority:30;
      	mso-style-unhide:no;
      	mso-style-qformat:yes;
      	mso-style-link:"Sterkt sitat Tegn";
      	mso-style-next:Normal;
      	margin-top:12.0pt;
      	margin-right:46.8pt;
      	margin-bottom:12.0pt;
      	margin-left:46.8pt;
      	text-align:center;
      	mso-pagination:widow-orphan;
      	border:none;
      	mso-border-top-alt:solid #ED7D31 3.0pt;
      	mso-border-top-themecolor:accent2;
      	padding:0cm;
      	mso-padding-alt:4.0pt 0cm 0cm 0cm;
      	font-size:12.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	mso-fareast-language:EN-US;}
      span.MsoSubtleEmphasis
      	{mso-style-priority:19;
      	mso-style-unhide:no;
      	mso-style-qformat:yes;
      	color:#595959;
      	mso-themecolor:text1;
      	mso-themetint:166;
      	font-style:italic;}
      span.MsoIntenseEmphasis
      	{mso-style-priority:21;
      	mso-style-unhide:no;
      	mso-style-qformat:yes;
      	font-variant:normal !important;
      	color:#ED7D31;
      	mso-themecolor:accent2;
      	text-transform:none;
      	font-weight:bold;
      	font-style:italic;
      	text-decoration:none;
      	text-line-through:none;}
      span.MsoSubtleReference
      	{mso-style-priority:31;
      	mso-style-unhide:no;
      	mso-style-qformat:yes;
      	font-variant:small-caps;
      	color:#404040;
      	mso-themecolor:text1;
      	mso-themetint:191;
      	text-transform:none;
      	letter-spacing:0pt;
      	text-underline:#7F7F7F;
      	text-decoration:underline;
      	text-underline:single;
      	mso-text-underline-themecolor:text1;
      	mso-text-underline-themetint:128;}
      span.MsoIntenseReference
      	{mso-style-priority:32;
      	mso-style-unhide:no;
      	mso-style-qformat:yes;
      	font-variant:small-caps;
      	color:windowtext;
      	text-transform:none;
      	letter-spacing:0pt;
      	font-weight:bold;
      	text-decoration:underline;
      	text-underline:single;}
      span.MsoBookTitle
      	{mso-style-priority:33;
      	mso-style-unhide:no;
      	mso-style-qformat:yes;
      	font-variant:small-caps;
      	text-transform:none;
      	letter-spacing:0pt;
      	font-weight:bold;}
      p.MsoTocHeading, li.MsoTocHeading, div.MsoTocHeading
      	{mso-style-noshow:yes;
      	mso-style-priority:39;
      	mso-style-qformat:yes;
      	mso-style-parent:"Overskrift 1";
      	mso-style-next:Normal;
      	margin-top:18.0pt;
      	margin-right:0cm;
      	margin-bottom:6.0pt;
      	margin-left:0cm;
      	mso-pagination:widow-orphan lines-together;
      	page-break-after:avoid;
      	border:none;
      	mso-border-bottom-alt:solid #ED7D31 .5pt;
      	mso-border-bottom-themecolor:accent2;
      	padding:0cm;
      	mso-padding-alt:0cm 0cm 2.0pt 0cm;
      	font-size:20.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#262626;
      	mso-themecolor:text1;
      	mso-themetint:217;
      	mso-fareast-language:EN-US;}
      span.Overskrift1Tegn
      	{mso-style-name:"Overskrift 1 Tegn";
      	mso-style-priority:9;
      	mso-style-unhide:no;
      	mso-style-locked:yes;
      	mso-style-link:"Overskrift 1";
      	mso-ansi-font-size:20.0pt;
      	mso-bidi-font-size:20.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#262626;
      	mso-themecolor:text1;
      	mso-themetint:217;}
      span.Overskrift2Tegn
      	{mso-style-name:"Overskrift 2 Tegn";
      	mso-style-noshow:yes;
      	mso-style-priority:9;
      	mso-style-unhide:no;
      	mso-style-locked:yes;
      	mso-style-link:"Overskrift 2";
      	mso-ansi-font-size:18.0pt;
      	mso-bidi-font-size:18.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#ED7D31;
      	mso-themecolor:accent2;}
      span.Overskrift3Tegn
      	{mso-style-name:"Overskrift 3 Tegn";
      	mso-style-noshow:yes;
      	mso-style-priority:9;
      	mso-style-unhide:no;
      	mso-style-locked:yes;
      	mso-style-link:"Overskrift 3";
      	mso-ansi-font-size:16.0pt;
      	mso-bidi-font-size:16.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#C45911;
      	mso-themecolor:accent2;
      	mso-themeshade:191;}
      span.Overskrift4Tegn
      	{mso-style-name:"Overskrift 4 Tegn";
      	mso-style-noshow:yes;
      	mso-style-priority:9;
      	mso-style-unhide:no;
      	mso-style-locked:yes;
      	mso-style-link:"Overskrift 4";
      	mso-ansi-font-size:14.0pt;
      	mso-bidi-font-size:14.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	font-style:italic;}
      span.Overskrift5Tegn
      	{mso-style-name:"Overskrift 5 Tegn";
      	mso-style-noshow:yes;
      	mso-style-priority:9;
      	mso-style-unhide:no;
      	mso-style-locked:yes;
      	mso-style-link:"Overskrift 5";
      	mso-ansi-font-size:12.0pt;
      	mso-bidi-font-size:12.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#C45911;
      	mso-themecolor:accent2;
      	mso-themeshade:191;}
      span.Overskrift6Tegn
      	{mso-style-name:"Overskrift 6 Tegn";
      	mso-style-noshow:yes;
      	mso-style-priority:9;
      	mso-style-unhide:no;
      	mso-style-locked:yes;
      	mso-style-link:"Overskrift 6";
      	mso-ansi-font-size:12.0pt;
      	mso-bidi-font-size:12.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	font-style:italic;}
      span.Overskrift7Tegn
      	{mso-style-name:"Overskrift 7 Tegn";
      	mso-style-noshow:yes;
      	mso-style-priority:9;
      	mso-style-unhide:no;
      	mso-style-locked:yes;
      	mso-style-link:"Overskrift 7";
      	mso-ansi-font-size:11.0pt;
      	mso-bidi-font-size:11.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	font-weight:bold;}
      span.Overskrift8Tegn
      	{mso-style-name:"Overskrift 8 Tegn";
      	mso-style-noshow:yes;
      	mso-style-priority:9;
      	mso-style-unhide:no;
      	mso-style-locked:yes;
      	mso-style-link:"Overskrift 8";
      	mso-ansi-font-size:11.0pt;
      	mso-bidi-font-size:11.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;}
      span.Overskrift9Tegn
      	{mso-style-name:"Overskrift 9 Tegn";
      	mso-style-noshow:yes;
      	mso-style-priority:9;
      	mso-style-unhide:no;
      	mso-style-locked:yes;
      	mso-style-link:"Overskrift 9";
      	mso-ansi-font-size:11.0pt;
      	mso-bidi-font-size:11.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#833C0B;
      	mso-themecolor:accent2;
      	mso-themeshade:128;
      	font-style:italic;}
      span.TittelTegn
      	{mso-style-name:"Tittel Tegn";
      	mso-style-priority:10;
      	mso-style-unhide:no;
      	mso-style-locked:yes;
      	mso-style-link:Tittel;
      	mso-ansi-font-size:48.0pt;
      	mso-bidi-font-size:48.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:#262626;
      	mso-themecolor:text1;
      	mso-themetint:217;}
      span.UndertittelTegn
      	{mso-style-name:"Undertittel Tegn";
      	mso-style-priority:11;
      	mso-style-unhide:no;
      	mso-style-locked:yes;
      	mso-style-link:Undertittel;
      	mso-ansi-font-size:14.0pt;
      	mso-bidi-font-size:14.0pt;
      	color:#404040;
      	mso-themecolor:text1;
      	mso-themetint:191;
      	text-transform:uppercase;
      	letter-spacing:1.0pt;}
      span.SitatTegn
      	{mso-style-name:"Sitat Tegn";
      	mso-style-priority:29;
      	mso-style-unhide:no;
      	mso-style-locked:yes;
      	mso-style-link:Sitat;
      	mso-ansi-font-size:12.0pt;
      	mso-bidi-font-size:12.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;
      	color:black;
      	mso-themecolor:text1;}
      span.SterktsitatTegn
      	{mso-style-name:"Sterkt sitat Tegn";
      	mso-style-priority:30;
      	mso-style-unhide:no;
      	mso-style-locked:yes;
      	mso-style-link:"Sterkt sitat";
      	mso-ansi-font-size:12.0pt;
      	mso-bidi-font-size:12.0pt;
      	font-family:"Calibri Light",sans-serif;
      	mso-ascii-font-family:"Calibri Light";
      	mso-ascii-theme-font:major-latin;
      	mso-fareast-font-family:"Times New Roman";
      	mso-fareast-theme-font:major-fareast;
      	mso-hansi-font-family:"Calibri Light";
      	mso-hansi-theme-font:major-latin;
      	mso-bidi-font-family:"Times New Roman";
      	mso-bidi-theme-font:major-bidi;}
      .MsoChpDefault
      	{mso-style-type:export-only;
      	mso-default-props:yes;
      	font-size:10.5pt;
      	mso-ansi-font-size:10.5pt;
      	mso-bidi-font-size:10.5pt;
      	font-family:"Calibri",sans-serif;
      	mso-ascii-font-family:Calibri;
      	mso-ascii-theme-font:minor-latin;
      	mso-fareast-font-family:"Times New Roman";
      	mso-fareast-theme-font:minor-fareast;
      	mso-hansi-font-family:Calibri;
      	mso-hansi-theme-font:minor-latin;
      	mso-bidi-font-family:"Times New Roman";
      	mso-bidi-theme-font:minor-bidi;
      	mso-fareast-language:EN-US;}
      .MsoPapDefault
      	{mso-style-type:export-only;
      	margin-bottom:8.0pt;
      	line-height:115%;}
      @page WordSection1
      	{size:595.3pt 841.9pt;
      	margin:72.0pt 72.0pt 72.0pt 72.0pt;
      	mso-header-margin:35.4pt;
      	mso-footer-margin:35.4pt;
      	mso-paper-source:0;}
      div.WordSection1
      	{page:WordSection1;}
      -->
      </style>
      <!--[if gte mso 10]>
      <style>
       /* Style Definitions */
       table.MsoNormalTable
      	{mso-style-name:"Vanlig tabell";
      	mso-tstyle-rowband-size:0;
      	mso-tstyle-colband-size:0;
      	mso-style-noshow:yes;
      	mso-style-priority:99;
      	mso-style-parent:"";
      	mso-padding-alt:0cm 5.4pt 0cm 5.4pt;
      	mso-para-margin-top:0cm;
      	mso-para-margin-right:0cm;
      	mso-para-margin-bottom:8.0pt;
      	mso-para-margin-left:0cm;
      	line-height:115%;
      	mso-pagination:widow-orphan;
      	font-size:10.5pt;
      	font-family:"Calibri",sans-serif;
      	mso-ascii-font-family:Calibri;
      	mso-ascii-theme-font:minor-latin;
      	mso-hansi-font-family:Calibri;
      	mso-hansi-theme-font:minor-latin;
      	mso-bidi-font-family:"Times New Roman";
      	mso-bidi-theme-font:minor-bidi;
      	mso-fareast-language:EN-US;}
      </style>
      <![endif]--><!--[if gte mso 9]><xml>
       <o:shapedefaults v:ext="edit" spidmax="1026"/>
      </xml><![endif]--><!--[if gte mso 9]><xml>
       <o:shapelayout v:ext="edit">
        <o:idmap v:ext="edit" data="1"/>
       </o:shapelayout></xml><![endif]-->
      </head>

      <body lang=EN-GB link="#0563C1" vlink="#954F72" style='tab-interval:36.0pt;
      word-wrap:break-word'>

      <div class=WordSection1>

      <div style='mso-element:para-border-div;border:none;border-bottom:solid #ED7D31 1.0pt;
      mso-border-bottom-themecolor:accent2;mso-border-bottom-alt:solid #ED7D31 .5pt;
      mso-border-bottom-themecolor:accent2;padding:0cm 0cm 2.0pt 0cm'>

      <h1>System finished processing.<o:p></o:p></h1>

      </div>

      <p class=MsoNormal>Excel sheet for job @Value(_FME_JOB_ID) with name
      @Value(_Projectname) can be downloaded here:</p>

      <p class=MsoNormal><a
      href="https://sensitivityatlas-norkart.fmecloud.com/fmedatadownload/results/@Value(_filename)">https://sensitivityatlas-norkart.fmecloud.com/fmedatadownload/results/@Value(_filename)</a></p>

      <p class=MsoNormal><o:p>&nbsp;</o:p></p>

      <p class=MsoNormal>Click here when ready for next processing step:</p>

      <p class=MsoNormal><a
      href="https://sensitivityatlas-norkart.fmecloud.com/fmeserver/apps/SensitivityAtlasProcessing">https://sensitivityatlas-norkart.fmecloud.com/fmeserver/apps/SensitivityAtlasProcessing</a><o:p></o:p></p>

      <p class=MsoNormal><o:p>&nbsp;</o:p></p>

      <p class=MsoNormal><o:p>&nbsp;</o:p></p>

      </div>

      </body>

      </html>
    FROM = noreply@norkart.no
    SERVICE = Generic SMTP
    SMTP_CONNECTION = HOST;smtp.office365.com;PORT;587;ENCRYPTION;TLS;TIMEOUT;60;AUTHENTICATION;YES;USERNAME;smtpnorkart@norkart.no;PASSWORD;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;FME_CONTROLLER_QUERY_FILE;dependencies/Generic SMTP.fme;FME_CONTROLLER_CHOICE;Generic SMTP
    SUBJECT = Sensitivity Atlas || Results for @Value(_Projectname) - JOBID @Value(_FME_JOB_ID)
    TO = $(Email)

Bookmark: Geopackage
Note: If mixed Coord sys date force evythng in same system

FME custom transformer SchemaSetter
This transformer adds both exposed and unexposed attributes to a feature-based schema, with appropriate data types. 
For example: if a feature has the following attributes:
Attribute(boolean) : 'mybool' has value 'Yes' 
Attribute(32 bit integer): 'myint' has value '12' 
Attribute(64 bit real) : 'myreal' has value '12.965' 
the following list attributes will be added:
Attribute(string) : 'attribute{0}.fme_data_type' has value 'fme_boolean' 
Attribute(encoded: utf-8): 'attribute{0}.name' has value 'mybool' 
Attribute(string) : 'attribute{1}.fme_data_type' has value 'fme_int32' 
Attribute(encoded: utf-8): 'attribute{1}.name' has value 'myint' 
Attribute(string) : 'attribute{2}.fme_data_type' has value 'fme_real64' 
Attribute(encoded: utf-8): 'attribute{2}.name' has value 'myreal' 
The transformer also gives users the option to exclude certain attributes based on name or prefix, and automatically excludes all "fme_" attributes.  Another option exists to force all attributes to string data type in the case of mismatches in the source attributes.
Input Ports 
Features containing attributes for which a schema definition is required. 
Output Ports 
All features are output. Attributes which have been selected to be excluded are removed from the feature. The list containing the schema of the feature is added to each feature. 
Parameters 
Attributes to Exclude 
A selected set of attributes that will be excluded from the generated schema list and removed from the feature.
Prefixes to Exclude 
A comma-delimited list of prefixes for attributes that are to be excluded from the generated schema list and removed from the feature. Regular expressions are not supported. For example: "date" will exclude any attributes that start with the letters "date" e.g. date_created, dateupdated
Sort Attributes 
(Ascending, Descending, None) Set this parameter to alphabetically sort output attributes.
Force attributes to strings:
If set to "No", the SchemaSetter will set the data type to the native attribute data type. If set to "Yes", the SchemaSetter will force all attribute data type sto "fme_char(255)".
Usage Notes 
The feature based schema can be passed to any writer that it set to Dynamic Mode and used with the "Schema from First Feature" setting.
Please see https://knowledge.safe.com/articles/1051/dynamic-workflow-tutorial-destination-schema-is-de-2.html for more information on feature-based schema using list attributes.

Parameters:
- AttributesToExclude =   # " " Attributes to exclude
- PrefixesToExclude =   # Prefixes to exclude
- SORT = None   # Sort Attributes
- ForceDataType = No   # Force attributes to strings?

Input_2 (input)
    -> ParameterFetcher
Note: Retrieve Parameters
ParameterFetcher
    ATTR_LIST = _AttributesToExclude $(AttributesToExclude) _PrefixesToExclude $(PrefixesToExclude) _sort $(SORT) _ForceDataType $(ForceDataType)
    -> PythonCaller
Note: See Comment in Code
PythonCaller
    PYTHONSOURCE:
      from __future__ import absolute_import, division, print_function, unicode_literals

      import fmeobjects
      import six

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedAttributes.append('_ForceDataType')
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              # sorting attributes
              if feature.getAttribute('_sort') == 'Ascending' or feature.getAttribute('_sort') == 'Descending':
                  attlist.sort()
                  if feature.getAttribute('_sort') == 'Descending':
                      attlist.reverse()

              for att in attlist:
                  if not StringInList(ExcludedAttributes,att) and not StringLikeList(ExcludedPrefixes,att) and not att=='_AttributesToExclude' and not att=='_PrefixesToExclude' and not att=='_sort':

                     #Check datatype and set in schema
                     if feature.getAttribute('_ForceDataType') == 'No':
                         type = feature.getAttributeType(att)
                         type = self.typesMapping[type]
                     #Force to string if user wishes
                     else:
                         type = "fme_char(255)"

                     if type is None:
                         feature.removeAttribute(att)
                     else:
                         #add schema attributes to feature
                         nfeature.setAttribute("attribute{"+str(i)+"}.fme_data_type",type)
                         nfeature.setAttribute("attribute{"+str(i)+"}.name",six.text_type(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              #print(i)
              self.pyoutput(nfeature)
          def close(self):
              pass
    PYTHONSYMBOL = FeatureProcessor
    -> Output_2 (output)
Output_2 (output)
