FME workspace Part1a_Dataset preparation_Import_data.fmw

Parameters:
- Folder_ = $(FME_MF_DIR)Inputdata\2004_SENSITIVITY_DATA\**\/   # Folder with input data
- DestDataset_SQLITE3FDO = $(FME_MF_DIR)Outputdata   # Folder to store the sqlite-database
- DestDataset_XLSXW = $(FME_MF_DIR)Outputdata\Feature_types_for_ranking.xls   # Excel-file with available feature-types in the dataset
- DestDataset_POSTGIS = dugong   # Connection

Readers:
- PATH_1: PATH from $(Folder_)
- NULL_1: NULL

Writers:
- POSTGIS_1: POSTGIS to $(DestDataset_POSTGIS)
- SQLITE3FDO_1: SQLITE3FDO to $(DestDataset_SQLITE3FDO)
- XLSXW_1: XLSXW to $(DestDataset_XLSXW)

Note: Reads all files in a folder
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> FeatureMerger [input 1]
Creator
    GEOMTYPE = Geometry Object
    NUM = 1
    CREATED -> TimeStamper
TimeStamper
    TIME_ATTR = _timestamp
    FMT = FME Date/Time (^Y^m^d^H^M^S)
    -> FeatureMerger [input 2]
FeatureMerger
    CONNECT_Z_MODE = First Wins
    MERGE_TYPE = Attributes Only
    SUPPLIERS_FIRST = No
    ATTR_CONFLICT_RES = Use Requestor
    JOIN_KEYS = 1 1 AUTO
    GEOM_TYPE = Build Polygons
    PROCESS_DUPS = Yes
    IGNORE_NULLS = No
    ATTR_ACCUM_MODE = Merge Supplier
    MERGED -> AttributeCreator_2
Note: POSTGIS
Table1 (writer POSTGIS_1)
Note: SQLITE
Table1 (writer SQLITE3FDO_1)
Aggregator_3
    GROUP_BY = fme_feature_type
    ACCUM_ATTRS_NAME = No
    MODE = Attributes Only
    ORDERED = No
    SEP = ,
    AGGREGATE -> AttributeExposer
AttributeExposer
    ATTR_LIST = fme_feature_type
    -> AttributeCreator
AttributeCreator
    ATTR_TABLE:
      SET_TO FromAttribute = fme_feature_type
      SET_TO FromValue = @Value(fme_feature_type)
      SET_TO ToAttribute = fme_feature_type
      SET_TO ToValue
    -> Sheet1 (writer XLSXW_1)
Sheet1 (writer XLSXW_1)
    attributes: FromAttribute auto(20), FromValue auto(20)

Bookmark: Format database tablenames
AttributeCreator_2
    ATTR_TABLE:
      SET_TO _folder = @Value(path_directory_windows)
      SET_TO _path_root = $(Folder_)
    -> StringReplacer_2
StringReplacer_2
    CASE = NO
    NO_MATCH = _FME_NO_OP_
    SRC_ATTRS = _path_root
    REGEXP = NO
    FIND_TEXT = \**\/
    -> StringReplacer_3
StringReplacer_3
    CASE = NO
    NO_MATCH = _FME_NO_OP_
    SRC_ATTRS = _path_root
    REGEXP = NO
    REPLACE_TEXT = \
    FIND_TEXT = /
    -> StringReplacer
StringReplacer
    CASE = NO
    NO_MATCH = _FME_NO_OP_
    SRC_ATTRS = _folder
    REGEXP = NO
    FIND_TEXT = @Value(_path_root)
    -> AttributeTrimmer
AttributeTrimmer
    TRIM_TO_NONE = Yes
    SRC_ATTRS = _folder
    TRIM_TYPE = Both
    TRIM_CHARS = \
    -> Aggregator [off]
    -> Tester
Tester
    TEST_DESCRIPTION = ""
    TEST_MODE = Automatic
    BOOL_OP = OR
    TEST_CLAUSE = TEST @Value(path_extension) = zip
    FAILED -> AttributeFilter
    PASSED -> FeatureReader_2

Bookmark: Read ZIP-files
FeatureReader_2
    COMBINE_GEOM = Use Result
    FEATURETYPES = PATH
    DATASET = @Value(path_windows)
    ATTR_CONFLICT_RES = Use Result
    PATH_GLOB_PATTERN = *
    FORMAT = PATH
    OUTPUT_FEATURES_DISPLAY = Schema and Data Features
    PATH_TYPE = ANY
    PATH_RETRIEVE_FILE_PROPERTIES = YES
    ATTR_ACCUM_MODE = Merge Initiator and Result
    <OTHER> -> FeatureReader_2__Generic_
    <OTHER> -> AttributeFilter
FeatureReader_2__Generic_: Inspector [off]

Bookmark: Sort filetypes
AttributeFilter
    ATTR_NAME = path_extension
    ATTR_VALUES:
      <EMPTY>,<MISSING>,<NULL>,<UNFILTERED>,
      dbf
      DBF
      DOC
      ini
      LYR
      mxd
      MXD
      MXT
      pptx
      prj
      PRJ
      SBN
      SBX
      shp
      SHP
      shx
      SHX
      txt
      XLS
      xml
      zip
      ,DBF,DOC,LYR,MXD,MXT,PRJ,SBN,SBX,SHP,SHX,XLS,dbf,ini,mxd,pptx,prj,shp,shx,txt,xml,zip
    xml -> AttributeFilter_zip
    txt -> AttributeFilter_zip
    XLS -> AttributeFilter_zip
    dbf DBF DOC ini LYR mxd MXD MXT pptx prj PRJ SBN SBX shp SHP shx SHX txt XLS xml zip -> AttributeFilter_zip
    <UNFILTERED> -> AttributeFilter_zip
    <NULL> -> AttributeFilter_zip
    <MISSING> -> AttributeFilter_zip
    <EMPTY> -> AttributeFilter_zip
    shp -> FeatureReader
    SHP -> FeatureReader
AttributeFilter_zip: Inspector [off]

Bookmark: Read data
FeatureReader
    INTERACT = <No Spatial Filter>
    ATTR_CONFLICT_RES = Use Result
    ESRISHAPE_UPPER_CASE_ATTR_NAMES = No
    ATTR_ACCUM_MODE = Merge Initiator and Result
    DATASET = @Value(path_windows)
    FORMAT = ESRISHAPE
    OUTPUT_FEATURES_DISPLAY = Schema and Data Features
    ESRISHAPE_CLIP_TO_ENVELOPE = NO
    ESRISHAPE_SIMPLE_DONUT_GEOMETRY = simple
    ESRISHAPE_USE_SEARCH_ENVELOPE = NO
    ESRISHAPE_CHECK_NUMERIC_FIELDS = yes
    COMBINE_GEOM = Use Result
    ESRISHAPE_DISSOLVE_HOLES = no
    <OTHER> -> CoordinateSystemExtractor

Bookmark: Find coordinate system
CoordinateSystemExtractor
    CRDSYS_ATTR = _coordsys
    -> Aggregator_2 [off]
    -> AttributeFilter_2
AttributeFilter_2
    ATTR_NAME = _coordsys
    ATTR_VALUES = <EMPTY>,<MISSING>,<NULL>,<UNFILTERED>,Accra.GhanaNational,_FME_0,_LL-27_0,_LL-WGS84_0
    Accra.GhanaNational -> Reprojector
    _FME_0 -> Reprojector
    _LL-27_0 -> Reprojector
    _LL-WGS84_0 -> Reprojector
    <UNFILTERED> -> AttributeFilter_2__Unfiltered_
    <NULL> -> AttributeFilter_2__Unfiltered_
    <MISSING> -> AttributeFilter_2__Unfiltered_
    <EMPTY> -> AttributeFilter_2__Unfiltered_
AttributeFilter_2__Unfiltered_: Inspector [off]
Reprojector
    RASTER_CELL_SIZE = Preserve Cells
    INTERPOLATION_TYPE_NAME = Nearest Neighbor
    DEST = EPSG:4326
    REPROJECTED -> AttributeCreator_4

Bookmark: Generate table names and schema
AttributeCreator_4
    ATTR_TABLE = SET_TO _fanout = i_@Value(_folder)_@Value(path_rootname)
    -> AttributeRemover
AttributeRemover
    REMOVE_ATTRS = path_type,path_created_date,path_ownername,path_readonly,path_modified_date,path_directory_windows,path_filesize,path_filename,path_unix,path_extension,_folder,path_accessed_date,path_rootname,_path_root,path_directory_unix
    -> SchemaSetter_adv
SchemaSetter_adv
    Only_varchar = fme_char(255)
    -> Table1 (writer POSTGIS_1) [off]
    -> Table1 (writer SQLITE3FDO_1)
    -> Aggregator_3

Bookmark: Find possible coordinate systems
Aggregator_2
    GROUP_BY = _coordsys
    ACCUM_ATTRS_NAME = No
    MODE = Geometry - Assemble One Level
    ORDERED = No
    SEP = ,
    AGGREGATE_TYPE = Homogeneous Collection (If Possible)
    AGGREGATE -> Aggregator_2_Aggregate
Aggregator_2_Aggregate: Inspector

Bookmark: Find possible file extensions
Aggregator
    GROUP_BY = path_extension
    ACCUM_ATTRS_NAME = No
    MODE = Geometry - Assemble One Level
    ORDERED = No
    SEP = ,
    AGGREGATE_TYPE = Homogeneous Collection (If Possible)
    AGGREGATE -> Aggregator_Aggregate
Aggregator_Aggregate: Inspector

FME custom transformer SchemaSetter_adv
This transformer adds both exposed and unexposed attributes to a feature-based schema, with appropriate data types. This means that if a feature has the following attributes:
    Attribute(boolean) : `mybool' has value `Yes'
    Attribute(32 bit integer): `myint' has value `12'
    Attribute(64 bit real) : `myreal' has value `12.965'
the following list attributes will be added:
    Attribute(string) : `attribute{0}.fme_data_type' has value `fme_boolean'
    Attribute(encoded: utf-8): `attribute{0}.name' has value `mybool'
    Attribute(string) : `attribute{1}.fme_data_type' has value `fme_int32'
    Attribute(encoded: utf-8): `attribute{1}.name' has value `myint'
    Attribute(string) : `attribute{2}.fme_data_type' has value `fme_real64'
    Attribute(encoded: utf-8): `attribute{2}.name' has value `myreal'
Please see http://fmepedia.safe.com/articles/Samples_and_Demos/Dynamic-Workflow-Tutorial-Destination-Schema-is-Derived-from-List-Attributes for more information on feature-based schema using list attributes.
The transformer also gives users the option to exclude certain attributes based on name or prefix, and automatically exludes all "fme_" attributes.
Attributes to Exclude: Choose any attribute(s) you wish to exclude from the dynamic schema
    Prefixes to Exclude: Enter a comma-delimited list of prefixes to be excluded form the dynamic schema
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- AttributesToExclude =   # " " Attributes to exclude
- PrefixesToExclude =   # Prefixes to exclude
- Only_varchar = fme_char(255)   # Set all to this type (for instance fme_char(255))

Input (input)
    -> ParameterFetcher
Note: Retrieve Parameters
ParameterFetcher
    ATTR_LIST = _AttributesToExclude {$(AttributesToExclude)} _PrefixesToExclude {$(PrefixesToExclude)} _Only_varchar {$(Only_varchar)}
    -> Tester
Tester
    TEST_DESCRIPTION = ""
    TEST_MODE = Automatic
    BOOL_OP = OR
    TEST_CLAUSE = TEST $(Only_varchar) NOT_ATTRIBUTE_VALUE_NULL ""
    PASSED -> PythonCaller_2
    FAILED -> PythonCaller_3
Note: All varchar255
PythonCaller_2
    PYTHONSYMBOL = FeatureProcessor
    PYTHONSOURCE:
      import fmeobjects

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              for att in attlist:
                  if not StringInList(ExcludedAttributes,att) and not StringLikeList(ExcludedPrefixes,att) and not att=='_AttributesToExclude' and not att=='_PrefixesToExclude':
                     type=feature.getAttributeType(att)
                     #Check datatype and set in schema
                     type = self.typesMapping[type]

                     if type is None:
                         feature.removeAttribute(att)
                     else:
                         #add schema attributes to feature
                         nfeature.setAttribute("attribute{"+str(i)+"}.fme_data_type",feature.getAttribute('_Only_varchar'))
                         nfeature.setAttribute("attribute{"+str(i)+"}.name",unicode(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              self.pyoutput(nfeature)
          def close(self):
              pass
    -> Output (output)
Note: See Comment in Code
PythonCaller_3
    PYTHONSYMBOL = FeatureProcessor
    PYTHONSOURCE:
      import fmeobjects

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              for att in attlist:
                  if not StringInList(ExcludedAttributes,att) and not StringLikeList(ExcludedPrefixes,att) and not att=='_AttributesToExclude' and not att=='_PrefixesToExclude':
                     type=feature.getAttributeType(att)
                     #Check datatype and set in schema
                     type = self.typesMapping[type]

                     if type is None:
                         feature.removeAttribute(att)
                     else:
                         #add schema attributes to feature
                         nfeature.setAttribute("attribute{"+str(i)+"}.fme_data_type",type)
                         nfeature.setAttribute("attribute{"+str(i)+"}.name",unicode(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              self.pyoutput(nfeature)
          def close(self):
              pass
    -> Output (output)
Output (output)
