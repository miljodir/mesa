FME workspace Part1b_Dataset preparation_Convert_to_specific_datatypes.fmw

Parameters:
- SQLITE_db = $(FME_MF_DIR)Outputdata\20160525070428\db.sl3   # SQLITE database containing both input and output data
- DestDataset_POSTGIS = dugong   # Connection

Readers:
- NULL_1: NULL
- SQLITE3FDO_1: SQLITE3FDO from $(SQLITE_db)

Writers:
- POSTGIS_1: POSTGIS to $(DestDataset_POSTGIS)
- SQLITE3FDO_2: SQLITE3FDO to $(SQLITE_db)

AttributeCreator_2
    ATTR_TABLE = SET_TO Ecosystem (Sandy Beaches) = 1
    -> AttributeFilter
AttributeFilter
    ATTR_NAME = FCODE
    ATTR_VALUES = <EMPTY>,<MISSING>,<NULL>,<UNFILTERED>,0,1007,1008,1009,1011,1012,1014,1015
    1009 -> AttributeKeeper_2
    1008 -> AttributeKeeper_2
AttributeKeeper_2
    KEEP_ATTRS = Ecosystem (Sandy Beaches)
    -> AttributeCreator_3
Note: POSTGIS
Table1 (writer POSTGIS_1)
Note: SQLITE
Table1 (writer SQLITE3FDO_2)
FeatureMerger_Merged: Inspector

Bookmark: Ecology
i_basemap_hydro_poly_hydro_poly (reader SQLITE3FDO_1)
    attributes: PRIMARYINDEX int64, _fanout char(255), PID char(255), SHAPE_GEOMETRY char(255), PERIMETER char(255), _coordsys char(255), AREA char(255), HYDRO_ID char(255), ANGLE char(255), _timestamp char(255), _Only_varchar char(255), HYDRO_ char(255), path_windows char(255), POLYGONID char(255), SCALE char(255), FCODE char(255), OBJECTID char(255), _creation_instance char(255)
    -> AttributeCreator_2
i_basemap_hydro_lines (reader SQLITE3FDO_1) [off]
    attributes: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
i_basemap_hydro_poly (reader SQLITE3FDO_1) [off]
    attributes: PRIMARYINDEX int64, _fanout char(255), PID char(255), SHAPE_GEOMETRY char(255), PERIMETER char(255), _coordsys char(255), AREA char(255), HYDRO_ID char(255), ANGLE char(255), _timestamp char(255), _Only_varchar char(255), HYDRO_ char(255), path_windows char(255), POLYGONID char(255), SCALE char(255), FCODE char(255), OBJECTID char(255), _creation_instance char(255)
    -> AttributeCreator_2
i_socio_economic_cultural_heritage_Historical_monuments (reader SQLITE3FDO_1)
    attributes: PRIMARYINDEX int64, SHAPE_GEOMETRY char(255), _creation_instance char(255), _timestamp char(255), Comment char(255), _coordsys char(255), _Only_varchar char(255), TypeID char(255), _fanout char(255), path_windows char(255), Id char(255), Name char(255)
    -> i_socio_economic_cultural_heritage_Historical_monuments
i_socio_economic_cultural_heritage_Historical_monuments: Inspector

Bookmark: Add Rank
Note: AttributeCreator_3 [AttributeCreator:8] / Substitute Missing, Null and Empty by: No Substitution / Set 'fme_feature_type' to 'E1' / Version: 8 / Last Parameter Edit: Build 16174
AttributeCreator_3
    ATTR_TABLE = SET_TO fme_feature_type = E1
    -> SchemaSetter_adv
Note: AttributeCreator_4 [AttributeCreator:8] / Substitute Missing, Null and Empty by: No Substitution / Set 'fme_feature_type' to 'E2' / Version: 8 / Last Parameter Edit: Build 16174
AttributeCreator_4
    ATTR_TABLE = SET_TO fme_feature_type = E2
    -> SchemaSetter_adv

Bookmark: Available features
i_socio_economic_human_use_Aquaculture (reader SQLITE3FDO_1) [off]
    attributes: PRIMARYINDEX int64, SHAPE_GEOMETRY char(255), _creation_instance char(255), _timestamp char(255), Comment char(255), _coordsys char(255), _Only_varchar char(255), TypeID char(255), _fanout char(255), path_windows char(255), Id char(255), Type char(255)
    -> i_socio_economic_human_use_Aquaculture [off]
i_socio_economic_human_use_Aquaculture: Inspector [off]
i_Rankings_Ecological_Ranking (reader SQLITE3FDO_1) [off]
    attributes: PRIMARYINDEX int64, _fanout char(255), _Only_varchar char(255), SHAPE_GEOMETRY char(255), Rank char(255), _timestamp char(255), _coordsys char(255), Segment_ID char(255), path_windows char(255), _creation_instance char(255)
    -> i_Rankings_Ecological_Ranking [off]
i_Rankings_Ecological_Ranking: Inspector [off]
i_Aerial_photos_Misc_XYphotolist (reader SQLITE3FDO_1) [off]
    attributes: PRIMARYINDEX int64, AREA char(255), _creation_instance char(255), RUN char(255), DATE_ char(255), HEIGHT char(255), path_windows char(255), _fanout char(255), LAT char(255), _timestamp char(255), LON char(255), GPSTIME char(255), SHAPE_GEOMETRY char(255), _coordsys char(255), PROJECT char(255), RMS_LO char(255), _Only_varchar char(255), PHOTO char(255), RMS_H char(255), RMS_LA char(255)
    -> i_Aerial_photos_Misc_XYphotolist [off]
i_Aerial_photos_Misc_XYphotolist: Inspector [off]
i_socio_economic_human_use_Mining_point (reader SQLITE3FDO_1) [off]
    attributes: PRIMARYINDEX int64, Id char(255), TypeID char(255), Prod_year char(255), _timestamp char(255), _coordsys char(255), SHAPE_GEOMETRY char(255), Type char(255), _creation_instance char(255), _Only_varchar char(255), Name char(255), path_windows char(255), _fanout char(255), Comment char(255)
    -> i_socio_economic_human_use_Mining_point [off]
i_socio_economic_human_use_Mining_point: Inspector [off]
i_basemap_Index_map_Ghana_bound_AGG (reader SQLITE3FDO_1) [off]
    attributes: PRIMARYINDEX int64, POPYREG char(255), _fanout char(255), POPYTYPE char(255), SHAPE_GEOMETRY char(255), PERIMETER char(255), _coordsys char(255), AREA char(255), FID_ char(255), _timestamp char(255), _Only_varchar char(255), POPYCOUN char(255), POPYADMIN char(255), BOUNDL_ID char(255), POPYTYPETX char(255), path_windows char(255), _creation_instance char(255), BOUNDL_ char(255)
    -> i_basemap_Index_map_Ghana_bound_AGG [off]
i_basemap_Index_map_Ghana_bound_AGG: Inspector [off]
i_Map_tiles_map_tiles_20000 (reader SQLITE3FDO_1) [off]
    attributes: PRIMARYINDEX int64, AREA char(255), SHAPE_GEOMETRY char(255), _creation_instance char(255), _timestamp char(255), _coordsys char(255), _Only_varchar char(255), _fanout char(255), path_windows char(255), ID char(255), PERIMETER char(255)
    -> i_Map_tiles_map_tiles_20000 [off]
i_Map_tiles_map_tiles_20000: Inspector [off]
i_socio_economic_human_use_Industrial_development (reader SQLITE3FDO_1) [off]
    attributes: PRIMARYINDEX int64, SHAPE_GEOMETRY char(255), _creation_instance char(255), _timestamp char(255), Comment char(255), _coordsys char(255), _Only_varchar char(255), TypeID char(255), _fanout char(255), path_windows char(255), Id char(255), Type char(255)
    -> i_socio_economic_human_use_Industrial_development [off]
i_socio_economic_human_use_Industrial_development: Inspector [off]
i_basemap_mp1 (reader SQLITE3FDO_1) [off]
    attributes: PRIMARYINDEX int64, _fanout char(255), _Only_varchar char(255), SHAPE_GEOMETRY char(255), _timestamp char(255), _coordsys char(255), Id char(255), path_windows char(255), _creation_instance char(255)
    -> i_basemap_mp1 [off]
i_basemap_mp1: Inspector [off]
i_basemap_hypso_line (reader SQLITE3FDO_1) [off]
    attributes: PRIMARYINDEX int64, HYPSO_ char(255), ZVAL char(255), _fanout char(255), SHAPE_GEOMETRY char(255), _coordsys char(255), HYPSO_ID char(255), LENGTH char(255), _timestamp char(255), _Only_varchar char(255), FNODE_ char(255), path_windows char(255), Shape_Leng char(255), RPOLY_ char(255), FCODE char(255), TNODE_ char(255), _creation_instance char(255), LPOLY_ char(255)
    -> i_basemap_hypso_line [off]
i_basemap_hypso_line: Inspector [off]
i_socio_economic_human_use_Tourism (reader SQLITE3FDO_1) [off]
    attributes: PRIMARYINDEX int64, SHAPE_GEOMETRY char(255), _creation_instance char(255), _timestamp char(255), Rooms char(255), Comment char(255), _coordsys char(255), _Only_varchar char(255), TypeID char(255), _fanout char(255), path_windows char(255), Id char(255), Name char(255)
    -> i_socio_economic_human_use_Tourism [off]
i_socio_economic_human_use_Tourism: Inspector [off]
i_ecological_protected_areas_National_poly (reader SQLITE3FDO_1) [off]
    attributes: PRIMARYINDEX int64, ISO3 char(255), IUCNCAT char(255), COUNTRY char(255), _creation_instance char(255), GISNAME char(255), path_windows char(255), STATUS char(255), _fanout char(255), SOURCE_ID char(255), Shape_Area char(255), LAT char(255), _timestamp char(255), LON char(255), AREANAME char(255), Shape_Leng char(255), SITE_CODE char(255), SHAPE_GEOMETRY char(255), _coordsys char(255), _Only_varchar char(255), DESIGNATE char(255)
    -> i_ecological_protected_areas_National_poly [off]
i_ecological_protected_areas_National_poly: Inspector [off]
i_socio_economic_fishery_Landing_Sites (reader SQLITE3FDO_1) [off]
    attributes: PRIMARYINDEX int64, _coordsys char(255), Id char(255), Canoes char(255), Region char(255), _timestamp char(255), _Only_varchar char(255), Village char(255), Fishermen char(255), SHAPE_GEOMETRY char(255), Hotels char(255), District char(255), _fanout char(255), path_windows char(255), _creation_instance char(255)
    -> i_socio_economic_fishery_Landing_Sites [off]
i_socio_economic_fishery_Landing_Sites: Inspector [off]
i_Rankings_Total_Ranking (reader SQLITE3FDO_1) [off]
    attributes: PRIMARYINDEX int64, BufferDist char(255), _fanout char(255), _Only_varchar char(255), SHAPE_GEOMETRY char(255), _timestamp char(255), _coordsys char(255), Id char(255), path_windows char(255), _creation_instance char(255)
    -> i_Rankings_Total_Ranking [off]
i_Rankings_Total_Ranking: Inspector [off]
i_socio_economic_populations_settlements_Regions (reader SQLITE3FDO_1) [off]
    attributes: PRIMARYINDEX int64, _coordsys char(255), Area_sqkm char(255), GHA_BND_ID char(255), FID_ char(255), GHA_BND_ char(255), _timestamp char(255), _Only_varchar char(255), REG_CODE char(255), AREA char(255), SHAPE_GEOMETRY char(255), REG_CAPITA char(255), PERIMETER char(255), _fanout char(255), path_windows char(255), _creation_instance char(255)
    -> i_socio_economic_populations_settlements_Regions [off]
i_socio_economic_populations_settlements_Regions: Inspector [off]
i_basemap_Index_map_Main_waterbodies_AGG (reader SQLITE3FDO_1) [off]
    attributes: PRIMARYINDEX int64, _coordsys char(255), FID_ char(255), _timestamp char(255), _Only_varchar char(255), WBODYL_ID char(255), AREA char(255), TYPE char(255), SHAPE_GEOMETRY char(255), WBODYL_ char(255), PERIMETER char(255), _fanout char(255), CONTENT char(255), _creation_instance char(255), path_windows char(255)
    -> i_basemap_Index_map_Main_waterbodies_AGG [off]
i_basemap_Index_map_Main_waterbodies_AGG: Inspector [off]
i_ecological_fauna_Birds (reader SQLITE3FDO_1) [off]
    attributes: PRIMARYINDEX int64, sp_interes char(255), SHAPE_GEOMETRY char(255), _creation_instance char(255), _timestamp char(255), comment char(255), _coordsys char(255), _Only_varchar char(255), _fanout char(255), path_windows char(255), Id char(255)
    -> i_ecological_fauna_Birds [off]
i_ecological_fauna_Birds: Inspector [off]
i_basemap_hypso_point (reader SQLITE3FDO_1) [off]
    attributes: PRIMARYINDEX int64, _coordsys char(255), FCODE char(255), HYPSO_ID char(255), ZVAL char(255), _timestamp char(255), _Only_varchar char(255), HYPSO_ char(255), AREA char(255), POLYGONID char(255), SHAPE_GEOMETRY char(255), ANGLE char(255), PERIMETER char(255), SCALE char(255), _fanout char(255), path_windows char(255), _creation_instance char(255)
    -> i_basemap_hypso_point [off]
i_basemap_hypso_point: Inspector [off]
i_Aerial_photos_Misc_Aerialphoto_locations (reader SQLITE3FDO_1) [off]
    attributes: PRIMARYINDEX int64, AREA char(255), _creation_instance char(255), RUN char(255), DATE_ char(255), HEIGHT char(255), path_windows char(255), _fanout char(255), LAT char(255), _timestamp char(255), LON char(255), GPSTIME char(255), SHAPE_GEOMETRY char(255), _coordsys char(255), PROJECT char(255), RMS_LO char(255), _Only_varchar char(255), PHOTO char(255), RMS_H char(255), RMS_LA char(255)
    -> i_Aerial_photos_Misc_Aerialphoto_locations [off]
i_Aerial_photos_Misc_Aerialphoto_locations: Inspector [off]
i_Aerial_photos_AGG_photolist (reader SQLITE3FDO_1) [off]
    attributes: PRIMARYINDEX int64, AREA char(255), _creation_instance char(255), RUN char(255), DATE_ char(255), HEIGHT char(255), path_windows char(255), _fanout char(255), LAT char(255), _timestamp char(255), LON char(255), GPSTIME char(255), SHAPE_GEOMETRY char(255), _coordsys char(255), PROJECT char(255), RMS_LO char(255), _Only_varchar char(255), PHOTO char(255), RMS_H char(255), RMS_LA char(255)
    -> i_Aerial_photos_AGG_photolist [off]
i_Aerial_photos_AGG_photolist: Inspector [off]
i_basemap_landform_point (reader SQLITE3FDO_1) [off]
    attributes: PRIMARYINDEX int64, _coordsys char(255), FCODE char(255), LANDFORM_ char(255), _timestamp char(255), _Only_varchar char(255), AREA char(255), POLYGONID char(255), SHAPE_GEOMETRY char(255), ANGLE char(255), LANDFORM_I char(255), PERIMETER char(255), SCALE char(255), _fanout char(255), path_windows char(255), _creation_instance char(255)
    -> i_basemap_landform_point [off]
i_basemap_landform_point: Inspector [off]
i_basemap_neat_poly (reader SQLITE3FDO_1) [off]
    attributes: PRIMARYINDEX int64, _coordsys char(255), Shape_Area char(255), NEAT_ID char(255), _timestamp char(255), Shape_Leng char(255), _Only_varchar char(255), AREA char(255), SHAPE_GEOMETRY char(255), NEAT_ char(255), TILE_NAME char(255), PERIMETER char(255), _fanout char(255), path_windows char(255), _creation_instance char(255)
    -> i_basemap_neat_poly [off]
i_basemap_neat_poly: Inspector [off]
i_physical_bathymetry_Bathymetri (reader SQLITE3FDO_1) [off]
    attributes: PRIMARYINDEX int64, _fanout char(255), _Only_varchar char(255), SHAPE_GEOMETRY char(255), _timestamp char(255), _coordsys char(255), VALUE char(255), path_windows char(255), _creation_instance char(255)
    -> i_physical_bathymetry_Bathymetri [off]
i_physical_bathymetry_Bathymetri: Inspector [off]
i_basemap_sd50k_poly (reader SQLITE3FDO_1) [off]
    attributes: PRIMARYINDEX int64, _coordsys char(255), Shape_Area char(255), SD50K_ID char(255), _timestamp char(255), Shape_Leng char(255), _Only_varchar char(255), SD50K_ char(255), AREA char(255), SD50K_NAME char(255), SHAPE_GEOMETRY char(255), PERIMETER char(255), _fanout char(255), path_windows char(255), _creation_instance char(255)
    -> i_basemap_sd50k_poly [off]
i_basemap_sd50k_poly: Inspector [off]
i_ecological_fauna_mammals (reader SQLITE3FDO_1) [off]
    attributes: PRIMARYINDEX int64, sp_interes char(255), SHAPE_GEOMETRY char(255), _creation_instance char(255), _timestamp char(255), endangered char(255), comment char(255), _coordsys char(255), _Only_varchar char(255), _fanout char(255), path_windows char(255), species char(255), Id char(255)
    -> i_ecological_fauna_mammals [off]
i_ecological_fauna_mammals: Inspector [off]
i_basemap_transpor_line (reader SQLITE3FDO_1) [off]
    attributes: PRIMARYINDEX int64, _coordsys char(255), RPOLY_ char(255), LPOLY_ char(255), FCODE char(255), LENGTH char(255), FNODE_ char(255), _timestamp char(255), Shape_Leng char(255), _Only_varchar char(255), TRANSPOR_ char(255), SHAPE_GEOMETRY char(255), TNODE_ char(255), _fanout char(255), path_windows char(255), _creation_instance char(255), TRANSPOR_I char(255)
    -> i_basemap_transpor_line [off]
i_basemap_transpor_line: Inspector [off]
i_basemap_Lables (reader SQLITE3FDO_1) [off]
    attributes: PRIMARYINDEX int64, _fanout char(255), SHAPE_GEOMETRY char(255), _coordsys char(255), OFFSETY char(255), TEXT char(255), SYMB_HLY char(255), _timestamp char(255), SYMBOL char(255), ID char(255), LEVEL char(255), JUSTIFY char(255), _Only_varchar char(255), path_windows char(255), OFFSETX char(255), FIT char(255), ALIGN char(255), _creation_instance char(255), SIZE char(255)
    -> i_basemap_Lables [off]
i_basemap_Lables: Inspector [off]
i_ecological_protected_areas_National_pnt_coast (reader SQLITE3FDO_1) [off]
    attributes: PRIMARYINDEX int64, AREANAME char(255), IUCN char(255), _fanout char(255), SHAPE_GEOMETRY char(255), COUNTRY char(255), _coordsys char(255), POLY char(255), DESIGNATE char(255), MARINE char(255), ISO3 char(255), _timestamp char(255), _Only_varchar char(255), LAT char(255), LON char(255), path_windows char(255), STATUS char(255), SITE_CODE char(255), _creation_instance char(255)
    -> i_ecological_protected_areas_National_pnt_coast [off]
i_ecological_protected_areas_National_pnt_coast: Inspector [off]
i_physical_costal_morphology_Coast_types (reader SQLITE3FDO_1) [off]
    attributes: PRIMARYINDEX int64, _fanout char(255), _Only_varchar char(255), SHAPE_GEOMETRY char(255), _timestamp char(255), _coordsys char(255), Sp_Interes char(255), ESI_Class char(255), path_windows char(255), _creation_instance char(255)
    -> i_physical_costal_morphology_Coast_types [off]
i_physical_costal_morphology_Coast_types: Inspector [off]
i_basemap_landform_line (reader SQLITE3FDO_1) [off]
    attributes: PRIMARYINDEX int64, _coordsys char(255), RPOLY_ char(255), LPOLY_ char(255), FCODE char(255), LENGTH char(255), FNODE_ char(255), LANDFORM_ char(255), _timestamp char(255), Shape_Leng char(255), _Only_varchar char(255), SHAPE_GEOMETRY char(255), LANDFORM_I char(255), TNODE_ char(255), _fanout char(255), path_windows char(255), _creation_instance char(255)
    -> i_basemap_landform_line [off]
i_basemap_landform_line: Inspector [off]
i_basemap_cult_point (reader SQLITE3FDO_1) [off]
    attributes: PRIMARYINDEX int64, _coordsys char(255), FCODE char(255), CULTURAL_I char(255), _timestamp char(255), _Only_varchar char(255), CULTURAL_ char(255), AREA char(255), POLYGONID char(255), SHAPE_GEOMETRY char(255), ANGLE char(255), PERIMETER char(255), SCALE char(255), _fanout char(255), path_windows char(255), _creation_instance char(255)
    -> i_basemap_cult_point [off]
i_basemap_cult_point: Inspector [off]
i_basemap_Index_map_Main_waterbodies_latlon (reader SQLITE3FDO_1) [off]
    attributes: PRIMARYINDEX int64, _coordsys char(255), FID_ char(255), _timestamp char(255), _Only_varchar char(255), WBODYL_ID char(255), AREA char(255), TYPE char(255), SHAPE_GEOMETRY char(255), WBODYL_ char(255), PERIMETER char(255), _fanout char(255), CONTENT char(255), _creation_instance char(255), path_windows char(255)
    -> i_basemap_Index_map_Main_waterbodies_latlon [off]
i_basemap_Index_map_Main_waterbodies_latlon: Inspector [off]
i_ecological_protected_areas_Internat_pnt (reader SQLITE3FDO_1) [off]
    attributes: PRIMARYINDEX int64, _coordsys char(255), AREANAME char(255), SITE_CODE char(255), CONV_CODE char(255), ISO3 char(255), LON char(255), _timestamp char(255), POLY char(255), _Only_varchar char(255), COUNTRY char(255), SHAPE_GEOMETRY char(255), LAT char(255), MARINE char(255), _fanout char(255), path_windows char(255), _creation_instance char(255)
    -> i_ecological_protected_areas_Internat_pnt [off]
i_ecological_protected_areas_Internat_pnt: Inspector [off]
i_basemap_Index_map_Ghana_bound_lonlat (reader SQLITE3FDO_1) [off]
    attributes: PRIMARYINDEX int64, POPYREG char(255), _fanout char(255), POPYTYPE char(255), SHAPE_GEOMETRY char(255), PERIMETER char(255), _coordsys char(255), AREA char(255), FID_ char(255), _timestamp char(255), _Only_varchar char(255), POPYCOUN char(255), POPYADMIN char(255), BOUNDL_ID char(255), POPYTYPETX char(255), path_windows char(255), _creation_instance char(255), BOUNDL_ char(255)
    -> i_basemap_Index_map_Ghana_bound_lonlat [off]
i_basemap_Index_map_Ghana_bound_lonlat: Inspector [off]
i_ecological_protected_areas_ramsar_sites (reader SQLITE3FDO_1) [off]
    attributes: PRIMARYINDEX int64, SHAPE_GEOMETRY char(255), _creation_instance char(255), _timestamp char(255), comment char(255), name char(255), _coordsys char(255), _Only_varchar char(255), _fanout char(255), path_windows char(255), ramsarId char(255), Id char(255)
    -> i_ecological_protected_areas_ramsar_sites [off]
i_ecological_protected_areas_ramsar_sites: Inspector [off]
i_basemap_utility_line (reader SQLITE3FDO_1) [off]
    attributes: PRIMARYINDEX int64, _coordsys char(255), RPOLY_ char(255), LPOLY_ char(255), FCODE char(255), LENGTH char(255), FNODE_ char(255), UTILITY_ char(255), UTILITY_ID char(255), _timestamp char(255), Shape_Leng char(255), _Only_varchar char(255), SHAPE_GEOMETRY char(255), TNODE_ char(255), _fanout char(255), path_windows char(255), _creation_instance char(255)
    -> i_basemap_utility_line [off]
i_basemap_utility_line: Inspector [off]
i_Aerial_photos_AerialPhotoFrame (reader SQLITE3FDO_1) [off]
    attributes: PRIMARYINDEX int64, _fanout char(255), _Only_varchar char(255), SHAPE_GEOMETRY char(255), _timestamp char(255), _coordsys char(255), Id char(255), path_windows char(255), _creation_instance char(255)
    -> i_Aerial_photos_AerialPhotoFrame [off]
i_Aerial_photos_AerialPhotoFrame: Inspector [off]
i_Aerial_photos_Misc_Oblique_photos (reader SQLITE3FDO_1) [off]
    attributes: PRIMARYINDEX int64, AREA char(255), _creation_instance char(255), RUN char(255), DATE_ char(255), HEIGHT char(255), path_windows char(255), _fanout char(255), LAT char(255), _timestamp char(255), LON char(255), GPSTIME char(255), SHAPE_GEOMETRY char(255), _coordsys char(255), PROJECT char(255), RMS_LO char(255), _Only_varchar char(255), PHOTO char(255), RMS_H char(255), RMS_LA char(255)
    -> i_Aerial_photos_Misc_Oblique_photos [off]
i_Aerial_photos_Misc_Oblique_photos: Inspector [off]
i_basemap_SEA (reader SQLITE3FDO_1) [off]
    attributes: PRIMARYINDEX int64, _fanout char(255), _Only_varchar char(255), SHAPE_GEOMETRY char(255), _timestamp char(255), _coordsys char(255), Id char(255), path_windows char(255), _creation_instance char(255)
    -> i_basemap_SEA [off]
i_basemap_SEA: Inspector [off]
i_Rankings_Human_Use_Ranking (reader SQLITE3FDO_1) [off]
    attributes: PRIMARYINDEX int64, _fanout char(255), _Only_varchar char(255), SHAPE_GEOMETRY char(255), Rank char(255), _timestamp char(255), _coordsys char(255), Segment_ID char(255), path_windows char(255), _creation_instance char(255)
    -> i_Rankings_Human_Use_Ranking [off]
i_Rankings_Human_Use_Ranking: Inspector [off]
i_socio_economic_human_use_Salt_Production (reader SQLITE3FDO_1) [off]
    attributes: PRIMARYINDEX int64, _fanout char(255), _Only_varchar char(255), SHAPE_GEOMETRY char(255), _timestamp char(255), _coordsys char(255), Comment char(255), Id char(255), path_windows char(255), _creation_instance char(255)
    -> i_socio_economic_human_use_Salt_Production [off]
i_socio_economic_human_use_Salt_Production: Inspector [off]
i_basemap_cult_poly (reader SQLITE3FDO_1) [off]
    attributes: PRIMARYINDEX int64, _coordsys char(255), FCODE char(255), Shape_Area char(255), _timestamp char(255), Shape_Leng char(255), CULT_POL_ char(255), _Only_varchar char(255), CULT_POL_I char(255), AREA char(255), SHAPE_GEOMETRY char(255), PERIMETER char(255), _fanout char(255), path_windows char(255), _creation_instance char(255)
    -> i_basemap_cult_poly [off]
i_basemap_cult_poly: Inspector [off]
i_ecological_protected_areas_Internat_poly (reader SQLITE3FDO_1) [off]
    attributes: PRIMARYINDEX int64, AREANAME char(255), _fanout char(255), SHAPE_GEOMETRY char(255), COUNTRY char(255), _coordsys char(255), GISNAME char(255), CONV_CODE char(255), ISO3 char(255), _timestamp char(255), _Only_varchar char(255), LAT char(255), LON char(255), SHAPE_area char(255), path_windows char(255), SITE_CODE char(255), _creation_instance char(255), SOURCE_ID char(255), SHAPE_len char(255)
    -> i_ecological_protected_areas_Internat_poly [off]
i_ecological_protected_areas_Internat_poly: Inspector [off]
i_ecological_protected_areas_Internat_pnt_coast (reader SQLITE3FDO_1) [off]
    attributes: PRIMARYINDEX int64, _coordsys char(255), AREANAME char(255), SITE_CODE char(255), CONV_CODE char(255), ISO3 char(255), LON char(255), _timestamp char(255), POLY char(255), _Only_varchar char(255), COUNTRY char(255), SHAPE_GEOMETRY char(255), LAT char(255), MARINE char(255), _fanout char(255), path_windows char(255), _creation_instance char(255)
    -> i_ecological_protected_areas_Internat_pnt_coast [off]
i_ecological_protected_areas_Internat_pnt_coast: Inspector [off]
i_Rankings_Coast_Class (reader SQLITE3FDO_1) [off]
    attributes: PRIMARYINDEX int64, SHAPE_GEOMETRY char(255), _creation_instance char(255), ET_ID char(255), _timestamp char(255), _coordsys char(255), CoastClass char(255), BufferDist char(255), _Only_varchar char(255), _fanout char(255), path_windows char(255), Id char(255)
    -> i_Rankings_Coast_Class [off]
i_Rankings_Coast_Class: Inspector [off]
i_basemap_transpor_point (reader SQLITE3FDO_1) [off]
    attributes: PRIMARYINDEX int64, _coordsys char(255), FCODE char(255), _timestamp char(255), _Only_varchar char(255), TRANSPOR_ char(255), AREA char(255), POLYGONID char(255), SHAPE_GEOMETRY char(255), ANGLE char(255), PERIMETER char(255), SCALE char(255), _fanout char(255), path_windows char(255), _creation_instance char(255), TRANSPOR_I char(255)
    -> i_basemap_transpor_point [off]
i_basemap_transpor_point: Inspector [off]
i_ecological_protected_areas_other_protected_areas (reader SQLITE3FDO_1) [off]
    attributes: PRIMARYINDEX int64, SHAPE_GEOMETRY char(255), _creation_instance char(255), _timestamp char(255), comment char(255), name char(255), _coordsys char(255), _Only_varchar char(255), _fanout char(255), path_windows char(255), site_Id char(255), Id char(255)
    -> i_ecological_protected_areas_other_protected_areas [off]
i_ecological_protected_areas_other_protected_areas: Inspector [off]
i_ecological_fauna_reptiles_and_lizards (reader SQLITE3FDO_1) [off]
    attributes: PRIMARYINDEX int64, Id char(255), _timestamp char(255), _coordsys char(255), SHAPE_GEOMETRY char(255), endangered char(255), _creation_instance char(255), _Only_varchar char(255), comment char(255), nesting char(255), sp_interes char(255), path_windows char(255), species char(255), _fanout char(255)
    -> i_ecological_fauna_reptiles_and_lizards [off]
i_ecological_fauna_reptiles_and_lizards: Inspector [off]
i_socio_economic_fishery_Fish_traps (reader SQLITE3FDO_1) [off]
    attributes: PRIMARYINDEX int64, SHAPE_GEOMETRY char(255), _creation_instance char(255), _timestamp char(255), Comment char(255), _coordsys char(255), _Only_varchar char(255), _fanout char(255), path_windows char(255), Id char(255), Type char(255)
    -> i_socio_economic_fishery_Fish_traps [off]
i_socio_economic_fishery_Fish_traps: Inspector [off]
i_ecological_protected_areas_National_pnt (reader SQLITE3FDO_1) [off]
    attributes: PRIMARYINDEX int64, AREANAME char(255), IUCN char(255), _fanout char(255), SHAPE_GEOMETRY char(255), COUNTRY char(255), _coordsys char(255), POLY char(255), DESIGNATE char(255), MARINE char(255), ISO3 char(255), _timestamp char(255), _Only_varchar char(255), LAT char(255), LON char(255), path_windows char(255), STATUS char(255), SITE_CODE char(255), _creation_instance char(255)
    -> i_ecological_protected_areas_National_pnt [off]
i_ecological_protected_areas_National_pnt: Inspector [off]
i_basemap_hydro_points (reader SQLITE3FDO_1) [off]
    attributes: PRIMARYINDEX int64, _coordsys char(255), HYDRO_ char(255), FCODE char(255), _timestamp char(255), HYDRO_ID char(255), _Only_varchar char(255), AREA char(255), POLYGONID char(255), SHAPE_GEOMETRY char(255), ANGLE char(255), PERIMETER char(255), SCALE char(255), _fanout char(255), path_windows char(255), _creation_instance char(255)
    -> i_basemap_hydro_points [off]
i_basemap_hydro_points: Inspector [off]
i_basemap_forest_poly (reader SQLITE3FDO_1) [off]
    attributes: PRIMARYINDEX int64, _coordsys char(255), FCODE char(255), FOREST_ID char(255), Shape_Area char(255), _timestamp char(255), Shape_Leng char(255), _Only_varchar char(255), AREA char(255), FOREST_ char(255), SHAPE_GEOMETRY char(255), PERIMETER char(255), _fanout char(255), path_windows char(255), _creation_instance char(255)
    -> i_basemap_forest_poly [off]
i_basemap_forest_poly: Inspector [off]
i_basemap_Join_Output (reader SQLITE3FDO_1) [off]
    attributes: PRIMARYINDEX int64, Avg_LENGTH char(255), FID_1 char(255), Avg_INTLBN char(255), _timestamp char(255), Avg_FNODE_ char(255), path_windows char(255), SHAPE_GEOMETRY char(255), RPOLY_ char(255), _fanout char(255), LPOLY_ char(255), Avg_RPOLY_ char(255), Count_ char(255), _creation_instance char(255), TNODE_ char(255), INTLBND_ID char(255), FNODE_ char(255), INTLBND_ char(255), Avg_TNODE_ char(255), _Only_varchar char(255), Avg_LPOLY_ char(255), Avg_INTL_1 char(255), LENGTH char(255), _coordsys char(255)
    -> i_basemap_Join_Output [off]
i_basemap_Join_Output: Inspector [off]
i_ecological_protected_areas_National_poly_coast (reader SQLITE3FDO_1) [off]
    attributes: PRIMARYINDEX int64, ISO3 char(255), IUCNCAT char(255), COUNTRY char(255), _creation_instance char(255), GISNAME char(255), path_windows char(255), STATUS char(255), _fanout char(255), SOURCE_ID char(255), Shape_Area char(255), LAT char(255), _timestamp char(255), LON char(255), AREANAME char(255), Shape_Leng char(255), SITE_CODE char(255), SHAPE_GEOMETRY char(255), _coordsys char(255), _Only_varchar char(255), DESIGNATE char(255)
    -> i_ecological_protected_areas_National_poly_coast [off]
i_ecological_protected_areas_National_poly_coast: Inspector [off]
i_ecological_fauna_fish_and_shrimps_points (reader SQLITE3FDO_1) [off]
    attributes: PRIMARYINDEX int64, sp_interes char(255), SHAPE_GEOMETRY char(255), _creation_instance char(255), _timestamp char(255), comment char(255), _coordsys char(255), _Only_varchar char(255), _fanout char(255), path_windows char(255), season char(255), Id char(255)
    -> i_ecological_fauna_fish_and_shrimps_points [off]
i_ecological_fauna_fish_and_shrimps_points: Inspector [off]
i_basemap_Sea_area (reader SQLITE3FDO_1) [off]
    attributes: PRIMARYINDEX int64, _coordsys char(255), RPOLY_ char(255), LPOLY_ char(255), HYDRO_ char(255), FCODE char(255), LENGTH char(255), FNODE_ char(255), _timestamp char(255), HYDRO_ID char(255), _Only_varchar char(255), SHAPE_LENG char(255), SHAPE_GEOMETRY char(255), TNODE_ char(255), _fanout char(255), path_windows char(255), _creation_instance char(255)
    -> i_basemap_Sea_area [off]
i_basemap_Sea_area: Inspector [off]

Bookmark: Generate table names and schema
SchemaSetter_adv
    Only_varchar = fme_char(255)
    -> Table1 (writer POSTGIS_1) [off]
    -> Table1 (writer SQLITE3FDO_2)
    -> FeatureMerger_Merged

FME custom transformer SchemaSetter_adv
This transformer adds both exposed and unexposed attributes to a feature-based schema, with appropriate data types. This means that if a feature has the following attributes:
    Attribute(boolean) : `mybool' has value `Yes'
    Attribute(32 bit integer): `myint' has value `12'
    Attribute(64 bit real) : `myreal' has value `12.965'
the following list attributes will be added:
    Attribute(string) : `attribute{0}.fme_data_type' has value `fme_boolean'
    Attribute(encoded: utf-8): `attribute{0}.name' has value `mybool'
    Attribute(string) : `attribute{1}.fme_data_type' has value `fme_int32'
    Attribute(encoded: utf-8): `attribute{1}.name' has value `myint'
    Attribute(string) : `attribute{2}.fme_data_type' has value `fme_real64'
    Attribute(encoded: utf-8): `attribute{2}.name' has value `myreal'
Please see http://fmepedia.safe.com/articles/Samples_and_Demos/Dynamic-Workflow-Tutorial-Destination-Schema-is-Derived-from-List-Attributes for more information on feature-based schema using list attributes.
The transformer also gives users the option to exclude certain attributes based on name or prefix, and automatically exludes all "fme_" attributes.
Attributes to Exclude: Choose any attribute(s) you wish to exclude from the dynamic schema
    Prefixes to Exclude: Enter a comma-delimited list of prefixes to be excluded form the dynamic schema
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- AttributesToExclude =   # " " Attributes to exclude
- PrefixesToExclude =   # Prefixes to exclude
- Only_varchar = fme_char(255)   # Set all to this type (for instance fme_char(255))

Input (input)
    -> ParameterFetcher
Note: Retrieve Parameters
ParameterFetcher
    ATTR_LIST = _AttributesToExclude {$(AttributesToExclude)} _PrefixesToExclude {$(PrefixesToExclude)} _Only_varchar {$(Only_varchar)}
    -> Tester
Tester
    TEST_DESCRIPTION = ""
    TEST_MODE = Automatic
    BOOL_OP = OR
    TEST_CLAUSE = TEST $(Only_varchar) NOT_ATTRIBUTE_VALUE_NULL ""
    PASSED -> PythonCaller_2
    FAILED -> PythonCaller_3
Note: All varchar255
PythonCaller_2
    PYTHONSYMBOL = FeatureProcessor
    PYTHONSOURCE:
      import fmeobjects

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              for att in attlist:
                  if not StringInList(ExcludedAttributes,att) and not StringLikeList(ExcludedPrefixes,att) and not att=='_AttributesToExclude' and not att=='_PrefixesToExclude':
                     type=feature.getAttributeType(att)
                     #Check datatype and set in schema
                     type = self.typesMapping[type]

                     if type is None:
                         feature.removeAttribute(att)
                     else:
                         #add schema attributes to feature
                         nfeature.setAttribute("attribute{"+str(i)+"}.fme_data_type",feature.getAttribute('_Only_varchar'))
                         nfeature.setAttribute("attribute{"+str(i)+"}.name",unicode(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              self.pyoutput(nfeature)
          def close(self):
              pass
    -> Output (output)
Note: See Comment in Code
PythonCaller_3
    PYTHONSYMBOL = FeatureProcessor
    PYTHONSOURCE:
      import fmeobjects

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              for att in attlist:
                  if not StringInList(ExcludedAttributes,att) and not StringLikeList(ExcludedPrefixes,att) and not att=='_AttributesToExclude' and not att=='_PrefixesToExclude':
                     type=feature.getAttributeType(att)
                     #Check datatype and set in schema
                     type = self.typesMapping[type]

                     if type is None:
                         feature.removeAttribute(att)
                     else:
                         #add schema attributes to feature
                         nfeature.setAttribute("attribute{"+str(i)+"}.fme_data_type",type)
                         nfeature.setAttribute("attribute{"+str(i)+"}.name",unicode(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              self.pyoutput(nfeature)
          def close(self):
              pass
    -> Output (output)
Output (output)
